--
-- GSC-MIB.my
-- MIB generated by MG-SOFT Visual MIB Builder Version 6.0  Build 88
-- Tuesday, January 12, 2016 at 18:05:09
--

--  
-- MIB generated by MG-SOFT Visual MIB Builder Version 6.0  Build 88
-- Tuesday, July 30, 2013 at 11:21:28
-- 
--  
-- MIB generated by MG-SOFT Visual MIB Builder Version 6.0  Build 88
-- Tuesday, July 16, 2013 at 11:11:27
-- 

	GSC-MIB DEFINITIONS ::= BEGIN
 
		IMPORTS
			OBJECT-GROUP, NOTIFICATION-GROUP			
				FROM SNMPv2-CONF			
			enterprises, TimeTicks, IpAddress, Unsigned32, OBJECT-TYPE, 
			MODULE-IDENTITY, NOTIFICATION-TYPE			
				FROM SNMPv2-SMI;
	
	
--   1.3.6.1.4.1.1
-- April 27, 2013 at 15:07 GMT
-- 1.3.6.1.4.1.1
-- April 27, 2013 at 15:07 GMT
		-- 1.3.6.1.4.1.12001
		gscAgentxMIB MODULE-IDENTITY 
			LAST-UPDATED "201506011515Z"		-- June 01, 2015 at 15:15 GMT
			ORGANIZATION 
				"ICT."
			CONTACT-INFO 
				"Contact-info."
			DESCRIPTION 
				"Description."
			::= { enterprises 12001 }

		
	
--
-- Type definitions
--
	
--  Type definitions
-- 
-- Type definitions
-- 
		LatitudeAndLongitude ::= OCTET STRING

		Float ::= OCTET STRING

	
--
-- Node definitions
--
	
--  Node definitions
-- 
-- Node definitions
-- 
-- 1.3.6.1.4.1.1.1
-- 1.3.6.1.4.1.1.1
		-- 1.3.6.1.4.1.12001.1
		gscConfigInfo OBJECT IDENTIFIER ::= { gscAgentxMIB 1 }

		
		-- 1.3.6.1.4.1.12001.1.1
		gscOmuIp OBJECT-TYPE
			SYNTAX IpAddress
			MAX-ACCESS read-only
			STATUS current
			DESCRIPTION
				"Description."
			::= { gscConfigInfo 1 }

		
		-- 1.3.6.1.4.1.12001.1.2
		gscOmuPort OBJECT-TYPE
			SYNTAX Unsigned32
			MAX-ACCESS read-write
			STATUS current
			DESCRIPTION
				"Description."
			::= { gscConfigInfo 2 }

		
		-- 1.3.6.1.4.1.12001.1.3
		gscSoftwareStatus OBJECT-TYPE
			SYNTAX INTEGER
				{
				dead(1),
				alive(2),
				unknowd(3)
				}
			MAX-ACCESS read-only
			STATUS current
			DESCRIPTION
				"Description."
			::= { gscConfigInfo 3 }

		
		-- 1.3.6.1.4.1.12001.1.4
		gscCoGRMIp OBJECT-TYPE
			SYNTAX IpAddress
			MAX-ACCESS read-write
			STATUS current
			DESCRIPTION
				"Description."
			::= { gscConfigInfo 4 }

		
		-- 1.3.6.1.4.1.12001.1.5
		gscCoGRMPortRemote OBJECT-TYPE
			SYNTAX Unsigned32
			MAX-ACCESS read-write
			STATUS current
			DESCRIPTION
				"Description."
			::= { gscConfigInfo 5 }

		
		-- 1.3.6.1.4.1.12001.1.6
		gscCoGRMPortLocal OBJECT-TYPE
			SYNTAX Unsigned32
			MAX-ACCESS read-write
			STATUS current
			DESCRIPTION
				"Description."
			::= { gscConfigInfo 6 }

		
		-- 1.3.6.1.4.1.12001.1.7
		gscCoCDUIp OBJECT-TYPE
			SYNTAX IpAddress
			MAX-ACCESS read-write
			STATUS current
			DESCRIPTION
				"Description."
			::= { gscConfigInfo 7 }

		
		-- 1.3.6.1.4.1.12001.1.8
		gscCoCDUPortRemote OBJECT-TYPE
			SYNTAX Unsigned32
			MAX-ACCESS read-write
			STATUS current
			DESCRIPTION
				"Description."
			::= { gscConfigInfo 8 }

		
		-- 1.3.6.1.4.1.12001.1.9
		gscCoCDUPortLocal OBJECT-TYPE
			SYNTAX Unsigned32
			MAX-ACCESS read-write
			STATUS current
			DESCRIPTION
				"Description."
			::= { gscConfigInfo 9 }

		
		-- 1.3.6.1.4.1.12001.1.10
		gscCoGTSNbapPortLocal OBJECT-TYPE
			SYNTAX Unsigned32
			MAX-ACCESS read-write
			STATUS current
			DESCRIPTION
				"Description."
			::= { gscConfigInfo 10 }

		
		-- 1.3.6.1.4.1.12001.1.11
		gscCoGTSFpSendPortLocal OBJECT-TYPE
			SYNTAX Unsigned32
			MAX-ACCESS read-write
			STATUS current
			DESCRIPTION
				"Description."
			::= { gscConfigInfo 11 }

		
		-- 1.3.6.1.4.1.12001.1.12
		gscCoGTSFpRecvPortLocal OBJECT-TYPE
			SYNTAX Unsigned32
			MAX-ACCESS read-write
			STATUS current
			DESCRIPTION
				"Description."
			::= { gscConfigInfo 12 }

		
		-- 1.3.6.1.4.1.12001.1.13
		gscCoBMCPortLocal OBJECT-TYPE
			SYNTAX Unsigned32
			MAX-ACCESS read-write
			STATUS current
			DESCRIPTION
				"Description."
			::= { gscConfigInfo 13 }

		
		-- 1.3.6.1.4.1.12001.1.14
		gscCoBMUPortLocal OBJECT-TYPE
			SYNTAX Unsigned32
			MAX-ACCESS read-write
			STATUS current
			DESCRIPTION
				"Description."
			::= { gscConfigInfo 14 }

		
		-- 1.3.6.1.4.1.12001.1.15
		gscCoCNTable OBJECT-TYPE
			SYNTAX SEQUENCE OF GscCoCNEntry
			MAX-ACCESS not-accessible
			STATUS current
			DESCRIPTION
				"Description."
			::= { gscConfigInfo 15 }

		
		-- 1.3.6.1.4.1.12001.1.15.1
		gscCoCNEntry OBJECT-TYPE
			SYNTAX GscCoCNEntry
			MAX-ACCESS not-accessible
			STATUS current
			DESCRIPTION
				"Description."
			INDEX { gscCoCNIndex }
			::= { gscCoCNTable 1 }

		
		GscCoCNEntry ::=
			SEQUENCE { 
				gscCoCNIndex
					Unsigned32,
				gscCoCNStatus
					INTEGER,
				gscCoCNIp
					IpAddress,
				gscCoCNSctpPortLocal
					Unsigned32,
				gscCoCNSctpPortRemote
					Unsigned32,
				gscCoCNRowStatus
					INTEGER
			 }

		-- 1.3.6.1.4.1.12001.1.15.1.1
		gscCoCNIndex OBJECT-TYPE
			SYNTAX Unsigned32 (1..65532)
			MAX-ACCESS not-accessible
			STATUS current
			DESCRIPTION
				"Description."
			::= { gscCoCNEntry 1 }

		
		-- 1.3.6.1.4.1.12001.1.15.1.2
		gscCoCNStatus OBJECT-TYPE
			SYNTAX INTEGER
				{
				primary(1),
				reserve(2)
				}
			MAX-ACCESS read-create
			STATUS current
			DESCRIPTION
				"Description."
			::= { gscCoCNEntry 2 }

		
		-- 1.3.6.1.4.1.12001.1.15.1.3
		gscCoCNIp OBJECT-TYPE
			SYNTAX IpAddress
			MAX-ACCESS read-create
			STATUS current
			DESCRIPTION
				"Description."
			::= { gscCoCNEntry 3 }

		
		-- 1.3.6.1.4.1.12001.1.15.1.4
		gscCoCNSctpPortLocal OBJECT-TYPE
			SYNTAX Unsigned32
			MAX-ACCESS read-create
			STATUS current
			DESCRIPTION
				"Description."
			::= { gscCoCNEntry 4 }

		
		-- 1.3.6.1.4.1.12001.1.15.1.5
		gscCoCNSctpPortRemote OBJECT-TYPE
			SYNTAX Unsigned32
			MAX-ACCESS read-create
			STATUS current
			DESCRIPTION
				"Description."
			::= { gscCoCNEntry 5 }

		
		-- 1.3.6.1.4.1.12001.1.15.1.6
		gscCoCNRowStatus OBJECT-TYPE
			SYNTAX INTEGER
				{
				active(1),
				notInservice(2),
				notReady(3),
				createAndGo(4),
				createAndWait(5),
				destroy(6)
				}
			MAX-ACCESS read-create
			STATUS current
			DESCRIPTION
				"Description."
			::= { gscCoCNEntry 6 }

		
--   1.3.6.1.4.1.1.3
-- 1.3.6.1.4.1.1.3
		-- 1.3.6.1.4.1.12001.2
		gscPerfTaskInfo OBJECT IDENTIFIER ::= { gscAgentxMIB 2 }

		
		-- 1.3.6.1.4.1.12001.2.1
		perfTaskTable OBJECT-TYPE
			SYNTAX SEQUENCE OF PerfTaskEntry
			MAX-ACCESS not-accessible
			STATUS current
			DESCRIPTION
				"Description."
			::= { gscPerfTaskInfo 1 }

		
		-- 1.3.6.1.4.1.12001.2.1.1
		perfTaskEntry OBJECT-TYPE
			SYNTAX PerfTaskEntry
			MAX-ACCESS not-accessible
			STATUS current
			DESCRIPTION
				"Description."
			INDEX { perfTaskIndex }
			::= { perfTaskTable 1 }

		
		PerfTaskEntry ::=
			SEQUENCE { 
				perfTaskIndex
					Unsigned32,
				perfTaskEnable
					INTEGER,
				perfTaskID
					Unsigned32,
				perfTaskBeginTime
					TimeTicks,
				perfTaskEndTime
					TimeTicks,
				perfTaskFetchTimeInterval
					INTEGER,
				perfTaskFetchDustSize
					Unsigned32,
				perfTaskEnableBeamNum
					Unsigned32,
				perfTaskEnableCarrierFreq
					Unsigned32,
				perfTaskTarget
					INTEGER,
				perfTaskRowStatus
					INTEGER
			 }

		-- 1.3.6.1.4.1.12001.2.1.1.1
		perfTaskIndex OBJECT-TYPE
			SYNTAX Unsigned32 (1..65532)
			MAX-ACCESS not-accessible
			STATUS current
			DESCRIPTION
				"Description."
			::= { perfTaskEntry 1 }

		
		-- 1.3.6.1.4.1.12001.2.1.1.2
		perfTaskEnable OBJECT-TYPE
			SYNTAX INTEGER
				{
				disable(0),
				enable(1)
				}
			MAX-ACCESS read-create
			STATUS current
			DESCRIPTION
				"Description."
			::= { perfTaskEntry 2 }

		
		-- 1.3.6.1.4.1.12001.2.1.1.3
		perfTaskID OBJECT-TYPE
			SYNTAX Unsigned32
			MAX-ACCESS read-create
			STATUS current
			DESCRIPTION
				"Description."
			::= { perfTaskEntry 3 }

		
		-- 1.3.6.1.4.1.12001.2.1.1.4
		perfTaskBeginTime OBJECT-TYPE
			SYNTAX TimeTicks
			MAX-ACCESS read-create
			STATUS current
			DESCRIPTION
				"Description."
			::= { perfTaskEntry 4 }

		
		-- 1.3.6.1.4.1.12001.2.1.1.5
		perfTaskEndTime OBJECT-TYPE
			SYNTAX TimeTicks
			MAX-ACCESS read-create
			STATUS current
			DESCRIPTION
				"Description."
			::= { perfTaskEntry 5 }

		
		-- 1.3.6.1.4.1.12001.2.1.1.6
		perfTaskFetchTimeInterval OBJECT-TYPE
			SYNTAX INTEGER
				{
				min15(1),
				min30(2),
				min45(3),
				min60(4)
				}
			MAX-ACCESS read-create
			STATUS current
			DESCRIPTION
				"Description."
			::= { perfTaskEntry 6 }

		
		-- 1.3.6.1.4.1.12001.2.1.1.7
		perfTaskFetchDustSize OBJECT-TYPE
			SYNTAX Unsigned32
			MAX-ACCESS read-create
			STATUS current
			DESCRIPTION
				"Description."
			::= { perfTaskEntry 7 }

		
		-- 1.3.6.1.4.1.12001.2.1.1.8
		perfTaskEnableBeamNum OBJECT-TYPE
			SYNTAX Unsigned32
			MAX-ACCESS read-create
			STATUS current
			DESCRIPTION
				"Description."
			::= { perfTaskEntry 8 }

		
		-- 1.3.6.1.4.1.12001.2.1.1.9
		perfTaskEnableCarrierFreq OBJECT-TYPE
			SYNTAX Unsigned32
			MAX-ACCESS read-create
			STATUS current
			DESCRIPTION
				"Description."
			::= { perfTaskEntry 9 }

		
		-- 1.3.6.1.4.1.12001.2.1.1.10
		perfTaskTarget OBJECT-TYPE
			SYNTAX INTEGER
				{
				normalPublicControlChannelReso(1),
				normalAccessCall(2),
				normalAccessCalled(3),
				normalAccessPSData(4),
				normalRandomAccess(5),
				normalMESLink(6),
				normalGWLink(7)
				}
			MAX-ACCESS read-create
			STATUS current
			DESCRIPTION
				"Description."
			::= { perfTaskEntry 10 }

		
		-- 1.3.6.1.4.1.12001.2.1.1.11
		perfTaskRowStatus OBJECT-TYPE
			SYNTAX INTEGER
				{
				active(1),
				notInService(2),
				notReady(3),
				createAndGo(4),
				createAndWait(5),
				destroy(6)
				}
			MAX-ACCESS read-create
			STATUS current
			DESCRIPTION
				"Description."
			::= { perfTaskEntry 11 }

		
--   1.3.6.1.4.1.1.4
-- 1.3.6.1.4.1.1.4
		-- 1.3.6.1.4.1.12001.3
		gscAlarmElements OBJECT IDENTIFIER ::= { gscAgentxMIB 3 }

		
--   1.3.6.1.4.1.1.4.1
-- 1.3.6.1.4.1.1.4.1
		-- 1.3.6.1.4.1.12001.3.1
		currentAlarmTable OBJECT-TYPE
			SYNTAX SEQUENCE OF CurrentAlarmEntry
			MAX-ACCESS not-accessible
			STATUS current
			DESCRIPTION
				"store the current alarms"
			::= { gscAlarmElements 1 }

		
--   1.3.6.1.4.1.1.4.1.1
-- 1.3.6.1.4.1.1.4.1.1
		-- 1.3.6.1.4.1.12001.3.1.1
		currentAlarmEntry OBJECT-TYPE
			SYNTAX CurrentAlarmEntry
			MAX-ACCESS not-accessible
			STATUS current
			DESCRIPTION
				"Description."
			INDEX { currentAlarmIndex }
			::= { currentAlarmTable 1 }

		
		CurrentAlarmEntry ::=
			SEQUENCE { 
				currentAlarmIndex
					Unsigned32,
				currentAlarmName
					OCTET STRING,
				currentAlarmNotifyOID
					OBJECT IDENTIFIER,
				currentAlarmRaisedTime
					TimeTicks,
				currentAlarmChangedTime
					TimeTicks,
				currentAlarmEventType
					INTEGER,
				currentAlarmProbableCause
					OCTET STRING,
				currentAlarmSpecificProblem
					OCTET STRING,
				currentAlarmPerceivedSeverity
					INTEGER,
				currentAlarmReportingMechanism
					INTEGER,
				currentAlarmDeviceID
					Unsigned32,
				currentAlarmDeviceType
					INTEGER,
				currentAlarmDeviceAddr
					IpAddress,
				currentAlarmAddtionalText
					OCTET STRING,
				currentAlarmProposeRepairAction
					OCTET STRING,
				currentAlarmClearAction
					INTEGER
			 }

--   1.3.6.1.4.1.1.4.1.1.1
-- 1.3.6.1.4.1.1.4.1.1.1
		-- 1.3.6.1.4.1.12001.3.1.1.1
		currentAlarmIndex OBJECT-TYPE
			SYNTAX Unsigned32 (1..65534)
			MAX-ACCESS not-accessible
			STATUS current
			DESCRIPTION
				"Description."
			::= { currentAlarmEntry 1 }

		
--   1.3.6.1.4.1.1.4.1.1.2
-- 1.3.6.1.4.1.1.4.1.1.2
		-- 1.3.6.1.4.1.12001.3.1.1.2
		currentAlarmName OBJECT-TYPE
			SYNTAX OCTET STRING
			MAX-ACCESS read-only
			STATUS current
			DESCRIPTION
				"Description."
			::= { currentAlarmEntry 2 }

		
--  1.3.6.1.4.1.1.4.1.1.3
		-- 1.3.6.1.4.1.12001.3.1.1.3
		currentAlarmNotifyOID OBJECT-TYPE
			SYNTAX OBJECT IDENTIFIER
			MAX-ACCESS read-only
			STATUS current
			DESCRIPTION
				"Description."
			::= { currentAlarmEntry 3 }

		
--   1.3.6.1.4.1.1.4.1.1.3
-- 1.3.6.1.4.1.1.4.1.1.4
		-- 1.3.6.1.4.1.12001.3.1.1.4
		currentAlarmRaisedTime OBJECT-TYPE
			SYNTAX TimeTicks
			UNITS "s"
			MAX-ACCESS read-only
			STATUS current
			DESCRIPTION
				"Description."
			::= { currentAlarmEntry 4 }

		
--   1.3.6.1.4.1.1.4.1.1.4
-- 1.3.6.1.4.1.1.4.1.1.5
		-- 1.3.6.1.4.1.12001.3.1.1.5
		currentAlarmChangedTime OBJECT-TYPE
			SYNTAX TimeTicks
			UNITS "s"
			MAX-ACCESS read-only
			STATUS current
			DESCRIPTION
				"Description."
			::= { currentAlarmEntry 5 }

		
--   1.3.6.1.4.1.1.4.1.1.5
-- 1.3.6.1.4.1.1.4.1.1.6
		-- 1.3.6.1.4.1.12001.3.1.1.6
		currentAlarmEventType OBJECT-TYPE
			SYNTAX INTEGER
				{
				communicationAlarm(1),
				deviceAlarm(2),
				dataProcessingAlarm(3),
				qualitySeriveAlarm(4),
				environmentAlarm(5),
				integrityAlarm(6),
				securityAlarm(7),
				timezoneAlarm(8),
				operationAlarm(9),
				physicalAlarm(10)
				}
			MAX-ACCESS read-only
			STATUS current
			DESCRIPTION
				"Description."
			::= { currentAlarmEntry 6 }

		
--   1.3.6.1.4.1.1.4.1.1.6
-- 1.3.6.1.4.1.1.4.1.1.7
		-- 1.3.6.1.4.1.12001.3.1.1.7
		currentAlarmProbableCause OBJECT-TYPE
			SYNTAX OCTET STRING
			MAX-ACCESS read-only
			STATUS current
			DESCRIPTION
				"Description."
			::= { currentAlarmEntry 7 }

		
--   1.3.6.1.4.1.1.4.1.1.7
-- 1.3.6.1.4.1.1.4.1.1.8
		-- 1.3.6.1.4.1.12001.3.1.1.8
		currentAlarmSpecificProblem OBJECT-TYPE
			SYNTAX OCTET STRING
			MAX-ACCESS read-only
			STATUS current
			DESCRIPTION
				"Description."
			::= { currentAlarmEntry 8 }

		
--   1.3.6.1.4.1.1.4.1.1.8
-- 1.3.6.1.4.1.1.4.1.1.9
		-- 1.3.6.1.4.1.12001.3.1.1.9
		currentAlarmPerceivedSeverity OBJECT-TYPE
			SYNTAX INTEGER
				{
				critical(1),
				major(2),
				minor(3),
				warning(4),
				indeterminate(5),
				cleared(6)
				}
			MAX-ACCESS read-only
			STATUS current
			DESCRIPTION
				"Description."
			::= { currentAlarmEntry 9 }

		
--  1.3.6.1.4.1.1.4.1.1.10
		-- 1.3.6.1.4.1.12001.3.1.1.10
		currentAlarmReportingMechanism OBJECT-TYPE
			SYNTAX INTEGER
				{
				expedited(1),
				pending(2),
				logged(3)
				}
			MAX-ACCESS read-only
			STATUS current
			DESCRIPTION
				"Description."
			::= { currentAlarmEntry 10 }

		
--   1.3.6.1.4.1.1.4.1.1.9
-- 1.3.6.1.4.1.1.4.1.1.11
		-- 1.3.6.1.4.1.12001.3.1.1.11
		currentAlarmDeviceID OBJECT-TYPE
			SYNTAX Unsigned32
			MAX-ACCESS read-only
			STATUS current
			DESCRIPTION
				"Description."
			::= { currentAlarmEntry 11 }

		
--   1.3.6.1.4.1.1.4.1.1.10
-- 1.3.6.1.4.1.1.4.1.1.12
		-- 1.3.6.1.4.1.12001.3.1.1.12
		currentAlarmDeviceType OBJECT-TYPE
			SYNTAX INTEGER
				{
				gscBoard(1),
				gtsBoard(2),
				lisuBoard(3)
				}
			MAX-ACCESS read-only
			STATUS current
			DESCRIPTION
				"Description."
			::= { currentAlarmEntry 12 }

		
--   1.3.6.1.4.1.1.4.1.1.11
-- 1.3.6.1.4.1.1.4.1.1.13
		-- 1.3.6.1.4.1.12001.3.1.1.13
		currentAlarmDeviceAddr OBJECT-TYPE
			SYNTAX IpAddress
			MAX-ACCESS read-only
			STATUS current
			DESCRIPTION
				"Description."
			::= { currentAlarmEntry 13 }

		
--   1.3.6.1.4.1.1.4.1.1.12
-- 1.3.6.1.4.1.1.4.1.1.14
		-- 1.3.6.1.4.1.12001.3.1.1.14
		currentAlarmAddtionalText OBJECT-TYPE
			SYNTAX OCTET STRING
			MAX-ACCESS read-only
			STATUS current
			DESCRIPTION
				"Description."
			::= { currentAlarmEntry 14 }

		
--   1.3.6.1.4.1.1.4.1.1.13
-- 1.3.6.1.4.1.1.4.1.1.15
		-- 1.3.6.1.4.1.12001.3.1.1.15
		currentAlarmProposeRepairAction OBJECT-TYPE
			SYNTAX OCTET STRING
			MAX-ACCESS read-only
			STATUS current
			DESCRIPTION
				"Description."
			::= { currentAlarmEntry 15 }

		
		-- 1.3.6.1.4.1.12001.3.1.1.16
		currentAlarmClearAction OBJECT-TYPE
			SYNTAX INTEGER
				{
				manual(0),
				automatic(1)
				}
			MAX-ACCESS read-only
			STATUS current
			DESCRIPTION
				"Description."
			::= { currentAlarmEntry 16 }

		
--   1.3.6.1.4.1.1.4.2
-- 1.3.6.1.4.1.1.4.2
		-- 1.3.6.1.4.1.12001.3.2
		supportedAlarmTable OBJECT-TYPE
			SYNTAX SEQUENCE OF SupportedAlarmEntry
			MAX-ACCESS not-accessible
			STATUS current
			DESCRIPTION
				"store all the supported alarms"
			::= { gscAlarmElements 2 }

		
--   1.3.6.1.4.1.1.4.2.1
-- 1.3.6.1.4.1.1.4.2.1
		-- 1.3.6.1.4.1.12001.3.2.1
		supportedAlarmEntry OBJECT-TYPE
			SYNTAX SupportedAlarmEntry
			MAX-ACCESS not-accessible
			STATUS current
			DESCRIPTION
				"Description."
			INDEX { supportedAlarmIndex }
			::= { supportedAlarmTable 1 }

		
		SupportedAlarmEntry ::=
			SEQUENCE { 
				supportedAlarmIndex
					Unsigned32,
				supportedAlarmName
					OCTET STRING,
				supportedAlarmNotifyOID
					OBJECT IDENTIFIER,
				supportedAlarmEventType
					INTEGER,
				supportedAlarmProbableCause
					OCTET STRING,
				supportedAlarmPerceivedSeverity
					INTEGER,
				supportedAlarmProposeRepairAction
					OCTET STRING,
				supportedAlarmReportingMechanism
					INTEGER,
				supportedAlarmClearAction
					INTEGER
			 }

--   1.3.6.1.4.1.1.4.2.1.1
-- 1.3.6.1.4.1.1.4.2.1.1
		-- 1.3.6.1.4.1.12001.3.2.1.1
		supportedAlarmIndex OBJECT-TYPE
			SYNTAX Unsigned32 (1..65534)
			MAX-ACCESS not-accessible
			STATUS current
			DESCRIPTION
				"Description."
			::= { supportedAlarmEntry 1 }

		
--   1.3.6.1.4.1.1.4.2.1.2
-- 1.3.6.1.4.1.1.4.2.1.2
		-- 1.3.6.1.4.1.12001.3.2.1.2
		supportedAlarmName OBJECT-TYPE
			SYNTAX OCTET STRING
			MAX-ACCESS read-only
			STATUS current
			DESCRIPTION
				"Description."
			::= { supportedAlarmEntry 2 }

		
--   1.3.6.1.4.1.1.4.2.1.3
-- 1.3.6.1.4.1.1.4.2.1.3
		-- 1.3.6.1.4.1.12001.3.2.1.3
		supportedAlarmNotifyOID OBJECT-TYPE
			SYNTAX OBJECT IDENTIFIER
			MAX-ACCESS read-only
			STATUS current
			DESCRIPTION
				"Description."
			::= { supportedAlarmEntry 3 }

		
--   1.3.6.1.4.1.1.4.2.1.4
-- 1.3.6.1.4.1.1.4.2.1.4
		-- 1.3.6.1.4.1.12001.3.2.1.4
		supportedAlarmEventType OBJECT-TYPE
			SYNTAX INTEGER
				{
				commnicationAlarm(1),
				deviceAlarm(2),
				dataProcessingAlarm(3),
				qualityServiceAlarm(4),
				environmentAlarm(5),
				integrityAlarm(6),
				securityAlarm(7),
				timezoneAlarm(8),
				operationAlarm(9),
				physicalAlarm(10)
				}
			MAX-ACCESS read-write
			STATUS current
			DESCRIPTION
				"Description."
			::= { supportedAlarmEntry 4 }

		
--   1.3.6.1.4.1.1.4.2.1.5
-- 1.3.6.1.4.1.1.4.2.1.5
		-- 1.3.6.1.4.1.12001.3.2.1.5
		supportedAlarmProbableCause OBJECT-TYPE
			SYNTAX OCTET STRING
			MAX-ACCESS read-only
			STATUS current
			DESCRIPTION
				"Description."
			::= { supportedAlarmEntry 5 }

		
--   1.3.6.1.4.1.1.4.2.1.7
-- 1.3.6.1.4.1.1.4.2.1.7
		-- 1.3.6.1.4.1.12001.3.2.1.6
		supportedAlarmPerceivedSeverity OBJECT-TYPE
			SYNTAX INTEGER
				{
				critical(1),
				major(2),
				minor(3),
				warning(4),
				indeterminate(5),
				cleared(6)
				}
			MAX-ACCESS read-write
			STATUS current
			DESCRIPTION
				"Description."
			::= { supportedAlarmEntry 6 }

		
		-- 1.3.6.1.4.1.12001.3.2.1.7
		supportedAlarmProposeRepairAction OBJECT-TYPE
			SYNTAX OCTET STRING
			MAX-ACCESS read-write
			STATUS current
			DESCRIPTION
				"Description."
			::= { supportedAlarmEntry 7 }

		
--   1.3.6.1.4.1.1.4.2.1.8
-- 1.3.6.1.4.1.1.4.2.1.8
		-- 1.3.6.1.4.1.12001.3.2.1.8
		supportedAlarmReportingMechanism OBJECT-TYPE
			SYNTAX INTEGER
				{
				expedited(1),
				pending(2),
				logged(3)
				}
			MAX-ACCESS read-write
			STATUS current
			DESCRIPTION
				"Description."
			::= { supportedAlarmEntry 8 }

		
		-- 1.3.6.1.4.1.12001.3.2.1.9
		supportedAlarmClearAction OBJECT-TYPE
			SYNTAX INTEGER
				{
				manual(0),
				automatic(1)
				}
			MAX-ACCESS read-write
			STATUS current
			DESCRIPTION
				"Description."
			::= { supportedAlarmEntry 9 }

		
--   1.3.6.1.4.1.1.6
-- 1.3.6.1.4.1.1.6
		-- 1.3.6.1.4.1.12001.4
		gscSoftWareRuntimeAlarms OBJECT IDENTIFIER ::= { gscAgentxMIB 4 }

		
--   1.3.6.1.4.1.1.6.1
-- 1.3.6.1.4.1.1.6.1
		-- 1.3.6.1.4.1.12001.4.1
		gscStartUp NOTIFICATION-TYPE
			OBJECTS { currentAlarmRaisedTime, currentAlarmAddtionalText }
			STATUS current
			DESCRIPTION 
				"Description."
			::= { gscSoftWareRuntimeAlarms 1 }

		
--   1.3.6.1.4.1.1.6.1
-- 1.3.6.1.4.1.1.6.1
		-- 1.3.6.1.4.1.12001.4.2
		softwareCrash NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { gscSoftWareRuntimeAlarms 2 }

		
--   1.3.6.1.4.1.1.6.2
-- 1.3.6.1.4.1.1.6.2
		-- 1.3.6.1.4.1.12001.4.3
		lanLinkFailure NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { gscSoftWareRuntimeAlarms 3 }

		
--   1.3.6.1.4.1.1.6.5
-- 1.3.6.1.4.1.1.6.5
		-- 1.3.6.1.4.1.12001.4.4
		serviceCapabilityFull NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { gscSoftWareRuntimeAlarms 4 }

		
--   1.3.6.1.4.1.1.6.9
-- 1.3.6.1.4.1.1.6.9
		-- 1.3.6.1.4.1.12001.4.5
		invalidConfigurationParameter NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { gscSoftWareRuntimeAlarms 5 }

		
--   1.3.6.1.4.1.1.6.11
-- 1.3.6.1.4.1.1.6.11
		-- 1.3.6.1.4.1.12001.4.6
		excessiveCPUusage NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { gscSoftWareRuntimeAlarms 6 }

		
--   1.3.6.1.4.1.1.6.12
-- 1.3.6.1.4.1.1.6.12
		-- 1.3.6.1.4.1.12001.4.7
		excessiveMemoryUsage NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { gscSoftWareRuntimeAlarms 7 }

		
--   1.3.6.1.4.1.1.6.17
-- 1.3.6.1.4.1.1.6.17
		-- 1.3.6.1.4.1.12001.4.8
		perfDataReport NOTIFICATION-TYPE
			OBJECTS { currentAlarmRaisedTime, currentAlarmChangedTime, currentAlarmSpecificProblem, currentAlarmDeviceID, currentAlarmDeviceType, 
				currentAlarmDeviceAddr }
			STATUS current
			DESCRIPTION 
				"Description."
			::= { gscSoftWareRuntimeAlarms 8 }

		
		-- 1.3.6.1.4.1.12001.5
		gscConfigInfoGroup OBJECT-GROUP
			OBJECTS { gscSoftwareStatus, gscCoGRMIp, gscCoGRMPortRemote, gscCoGRMPortLocal, gscCoCDUIp, 
				gscCoCDUPortRemote, gscCoCDUPortLocal, gscCoCNStatus, gscCoCNIp, gscCoCNSctpPortLocal, 
				gscCoCNSctpPortRemote, gscCoCNRowStatus, gscOmuIp, gscOmuPort, gscCoGTSNbapPortLocal, 
				gscCoGTSFpSendPortLocal, gscCoGTSFpRecvPortLocal, gscCoBMCPortLocal, gscCoBMUPortLocal }
			STATUS current
			DESCRIPTION 
				"Description."
			::= { gscAgentxMIB 5 }

		
		-- 1.3.6.1.4.1.12001.6
		gscPerfTaskInfoGroup OBJECT-GROUP
			OBJECTS { perfTaskEnable, perfTaskID, perfTaskBeginTime, perfTaskEndTime, perfTaskFetchTimeInterval, 
				perfTaskFetchDustSize, perfTaskEnableBeamNum, perfTaskEnableCarrierFreq, perfTaskTarget, perfTaskRowStatus
				 }
			STATUS current
			DESCRIPTION 
				"Description."
			::= { gscAgentxMIB 6 }

		
--   1.3.6.1.4.1.1.22
-- 1.3.6.1.4.1.1.22
		-- 1.3.6.1.4.1.12001.7
		gscAlarmGroup OBJECT-GROUP
			OBJECTS { currentAlarmName, currentAlarmNotifyOID, currentAlarmRaisedTime, currentAlarmChangedTime, currentAlarmEventType, 
				currentAlarmProbableCause, currentAlarmSpecificProblem, currentAlarmPerceivedSeverity, currentAlarmReportingMechanism, currentAlarmDeviceID, 
				currentAlarmDeviceType, currentAlarmDeviceAddr, currentAlarmAddtionalText, currentAlarmProposeRepairAction, currentAlarmClearAction, 
				supportedAlarmName, supportedAlarmNotifyOID, supportedAlarmEventType, supportedAlarmProbableCause, supportedAlarmPerceivedSeverity, 
				supportedAlarmProposeRepairAction, supportedAlarmReportingMechanism, supportedAlarmClearAction }
			STATUS current
			DESCRIPTION 
				"Description."
			::= { gscAgentxMIB 7 }

		
--   1.3.6.1.4.1.1.30
-- 1.3.6.1.4.1.1.30
		-- 1.3.6.1.4.1.12001.8
		notificationGroup NOTIFICATION-GROUP
			NOTIFICATIONS { gscStartUp, softwareCrash, lanLinkFailure, serviceCapabilityFull, invalidConfigurationParameter, 
				excessiveCPUusage, excessiveMemoryUsage, perfDataReport }
			STATUS current
			DESCRIPTION 
				"Description."
			::= { gscAgentxMIB 8 }

		
	
	END

--
-- GSC-MIB.my
--

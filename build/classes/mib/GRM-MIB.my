--
-- GRM-MIB.my
-- MIB generated by MG-SOFT Visual MIB Builder Version 6.0  Build 88
-- Thursday, January 21, 2016 at 10:59:01
--

--  
-- MIB generated by MG-SOFT Visual MIB Builder Version 6.0  Build 88
-- Tuesday, July 30, 2013 at 11:21:28
-- 
--  
-- MIB generated by MG-SOFT Visual MIB Builder Version 6.0  Build 88
-- Tuesday, July 16, 2013 at 11:11:27
-- 

	GRM-MIB DEFINITIONS ::= BEGIN
 
		IMPORTS
			OBJECT-GROUP, NOTIFICATION-GROUP			
				FROM SNMPv2-CONF			
			enterprises, TimeTicks, IpAddress, Unsigned32, OBJECT-TYPE, 
			MODULE-IDENTITY, NOTIFICATION-TYPE			
				FROM SNMPv2-SMI;
	
	
--   1.3.6.1.4.1.1
-- April 27, 2013 at 15:07 GMT
-- 1.3.6.1.4.1.1
-- April 27, 2013 at 15:07 GMT
		-- 1.3.6.1.4.1.11001
		grmAgentxMIB MODULE-IDENTITY 
			LAST-UPDATED "201510261515Z"		-- October 26, 2015 at 15:15 GMT
			ORGANIZATION 
				"ICT."
			CONTACT-INFO 
				"Contact-info."
			DESCRIPTION 
				"Description."
			::= { enterprises 11001 }

		
	
--
-- Type definitions
--
	
--  Type definitions
-- 
-- Type definitions
-- 
		LatitudeAndLongitude ::= OCTET STRING

		Float ::= OCTET STRING

	
--
-- Node definitions
--
	
		-- 1.3.6.1.4.1.11001.1
		gssConfigInfo OBJECT IDENTIFIER ::= { grmAgentxMIB 1 }

		
		-- 1.3.6.1.4.1.11001.1.1
		gssGwId OBJECT-TYPE
			SYNTAX Unsigned32
			MAX-ACCESS read-write
			STATUS current
			DESCRIPTION
				"Description."
			::= { gssConfigInfo 1 }

		
		-- 1.3.6.1.4.1.11001.1.2
		gssGwType OBJECT-TYPE
			SYNTAX INTEGER
				{
				i(0),
				m(1)
				}
			MAX-ACCESS read-write
			STATUS current
			DESCRIPTION
				"Description."
			::= { gssConfigInfo 2 }

		
		-- 1.3.6.1.4.1.11001.1.3
		gssLongtitude OBJECT-TYPE
			SYNTAX OCTET STRING
			MAX-ACCESS read-write
			STATUS current
			DESCRIPTION
				"Description."
			::= { gssConfigInfo 3 }

		
		-- 1.3.6.1.4.1.11001.1.4
		gssLatitude OBJECT-TYPE
			SYNTAX OCTET STRING
			MAX-ACCESS read-write
			STATUS current
			DESCRIPTION
				"Description."
			::= { gssConfigInfo 4 }

		
		-- 1.3.6.1.4.1.11001.1.5
		gssPrimaryMode OBJECT-TYPE
			SYNTAX INTEGER
				{
				guest(0),
				owner(1)
				}
			MAX-ACCESS read-write
			STATUS current
			DESCRIPTION
				"Description."
			::= { gssConfigInfo 5 }

		
		-- 1.3.6.1.4.1.11001.1.6
		gssFrameStartTime OBJECT-TYPE
			SYNTAX Unsigned32
			MAX-ACCESS read-write
			STATUS current
			DESCRIPTION
				"Description."
			::= { gssConfigInfo 6 }

		
		-- 1.3.6.1.4.1.11001.1.7
		gssConfigMaxEIRP OBJECT-TYPE
			SYNTAX OCTET STRING
			MAX-ACCESS read-write
			STATUS current
			DESCRIPTION
				"Description."
			::= { gssConfigInfo 7 }

		
		-- 1.3.6.1.4.1.11001.1.8
		gssSupportMaxEIRP OBJECT-TYPE
			SYNTAX OCTET STRING
			MAX-ACCESS read-write
			STATUS current
			DESCRIPTION
				"Description."
			::= { gssConfigInfo 8 }

		
		-- 1.3.6.1.4.1.11001.1.9
		gscBeamAccessTable OBJECT-TYPE
			SYNTAX SEQUENCE OF GscBeamAccessEntry
			MAX-ACCESS not-accessible
			STATUS current
			DESCRIPTION
				"Description."
			::= { gssConfigInfo 9 }

		
		-- 1.3.6.1.4.1.11001.1.9.1
		gscBeamAccessEntry OBJECT-TYPE
			SYNTAX GscBeamAccessEntry
			MAX-ACCESS not-accessible
			STATUS current
			DESCRIPTION
				"Description."
			INDEX { gscBeamAccessIndex }
			::= { gscBeamAccessTable 1 }

		
		GscBeamAccessEntry ::=
			SEQUENCE { 
				gscBeamAccessIndex
					Unsigned32,
				gscBeamAccessBeamId
					Unsigned32,
				gscBeamAccessMinSigValue
					Unsigned32,
				gscBeamAccessTimeoutCounter
					Unsigned32,
				gscBeamAccessAreaUpdatePeriod
					Unsigned32,
				gscBeamAccessMaxRetry
					Unsigned32,
				gscBeamAccessDenyWaitTime
					Unsigned32,
				gscBeamAccessPermitBlockNum
					Unsigned32,
				gscBeamAccessUeMaxPower
					OCTET STRING,
				gscBeamAccessDacchAssignTimeout
					Unsigned32,
				gscBeamAccessDtchAssignTimeout
					Unsigned32,
				gscBeamAccessDtchDelayReleaseTimeout
					Unsigned32,
				gscBeamAccessPacketRemain
					Unsigned32,
				gscBeamAccessRouteUpdatePeriod
					Unsigned32,
				gscBeamAccessPacketWaitUpAssignTimeout
					Unsigned32,
				gscBeamAccessPacketDenyWaitTimeout
					Unsigned32,
				gscBeamAccessPdtchAssignTimeout
					Unsigned32,
				gscBeamAccessPacketRqTimeout
					Unsigned32,
				gscBeamAccessReportTime
					Unsigned32,
				gscBeamAccessRowstatus
					INTEGER
			 }

		-- 1.3.6.1.4.1.11001.1.9.1.1
		gscBeamAccessIndex OBJECT-TYPE
			SYNTAX Unsigned32 (1..65532)
			MAX-ACCESS not-accessible
			STATUS current
			DESCRIPTION
				"Description."
			::= { gscBeamAccessEntry 1 }

		
		-- 1.3.6.1.4.1.11001.1.9.1.2
		gscBeamAccessBeamId OBJECT-TYPE
			SYNTAX Unsigned32
			MAX-ACCESS read-create
			STATUS current
			DESCRIPTION
				"Description."
			::= { gscBeamAccessEntry 2 }

		
		-- 1.3.6.1.4.1.11001.1.9.1.3
		gscBeamAccessMinSigValue OBJECT-TYPE
			SYNTAX Unsigned32
			MAX-ACCESS read-create
			STATUS current
			DESCRIPTION
				"Description."
			::= { gscBeamAccessEntry 3 }

		
		-- 1.3.6.1.4.1.11001.1.9.1.4
		gscBeamAccessTimeoutCounter OBJECT-TYPE
			SYNTAX Unsigned32
			MAX-ACCESS read-create
			STATUS current
			DESCRIPTION
				"Description."
			::= { gscBeamAccessEntry 4 }

		
		-- 1.3.6.1.4.1.11001.1.9.1.5
		gscBeamAccessAreaUpdatePeriod OBJECT-TYPE
			SYNTAX Unsigned32
			MAX-ACCESS read-create
			STATUS current
			DESCRIPTION
				"Description."
			::= { gscBeamAccessEntry 5 }

		
		-- 1.3.6.1.4.1.11001.1.9.1.6
		gscBeamAccessMaxRetry OBJECT-TYPE
			SYNTAX Unsigned32
			MAX-ACCESS read-create
			STATUS current
			DESCRIPTION
				"Description."
			::= { gscBeamAccessEntry 6 }

		
		-- 1.3.6.1.4.1.11001.1.9.1.7
		gscBeamAccessDenyWaitTime OBJECT-TYPE
			SYNTAX Unsigned32
			MAX-ACCESS read-create
			STATUS current
			DESCRIPTION
				"Description."
			::= { gscBeamAccessEntry 7 }

		
		-- 1.3.6.1.4.1.11001.1.9.1.8
		gscBeamAccessPermitBlockNum OBJECT-TYPE
			SYNTAX Unsigned32
			MAX-ACCESS read-create
			STATUS current
			DESCRIPTION
				"Description."
			::= { gscBeamAccessEntry 8 }

		
		-- 1.3.6.1.4.1.11001.1.9.1.9
		gscBeamAccessUeMaxPower OBJECT-TYPE
			SYNTAX OCTET STRING
			MAX-ACCESS read-create
			STATUS current
			DESCRIPTION
				"Description."
			::= { gscBeamAccessEntry 9 }

		
		-- 1.3.6.1.4.1.11001.1.9.1.10
		gscBeamAccessDacchAssignTimeout OBJECT-TYPE
			SYNTAX Unsigned32
			MAX-ACCESS read-create
			STATUS current
			DESCRIPTION
				"Description."
			::= { gscBeamAccessEntry 10 }

		
		-- 1.3.6.1.4.1.11001.1.9.1.11
		gscBeamAccessDtchAssignTimeout OBJECT-TYPE
			SYNTAX Unsigned32
			MAX-ACCESS read-create
			STATUS current
			DESCRIPTION
				"Description."
			::= { gscBeamAccessEntry 11 }

		
		-- 1.3.6.1.4.1.11001.1.9.1.12
		gscBeamAccessDtchDelayReleaseTimeout OBJECT-TYPE
			SYNTAX Unsigned32
			MAX-ACCESS read-create
			STATUS current
			DESCRIPTION
				"Description."
			::= { gscBeamAccessEntry 12 }

		
		-- 1.3.6.1.4.1.11001.1.9.1.13
		gscBeamAccessPacketRemain OBJECT-TYPE
			SYNTAX Unsigned32
			MAX-ACCESS read-create
			STATUS current
			DESCRIPTION
				"Description."
			::= { gscBeamAccessEntry 13 }

		
		-- 1.3.6.1.4.1.11001.1.9.1.14
		gscBeamAccessRouteUpdatePeriod OBJECT-TYPE
			SYNTAX Unsigned32
			MAX-ACCESS read-create
			STATUS current
			DESCRIPTION
				"Description."
			::= { gscBeamAccessEntry 14 }

		
		-- 1.3.6.1.4.1.11001.1.9.1.15
		gscBeamAccessPacketWaitUpAssignTimeout OBJECT-TYPE
			SYNTAX Unsigned32
			MAX-ACCESS read-create
			STATUS current
			DESCRIPTION
				"Description."
			::= { gscBeamAccessEntry 15 }

		
		-- 1.3.6.1.4.1.11001.1.9.1.16
		gscBeamAccessPacketDenyWaitTimeout OBJECT-TYPE
			SYNTAX Unsigned32
			MAX-ACCESS read-create
			STATUS current
			DESCRIPTION
				"Description."
			::= { gscBeamAccessEntry 16 }

		
		-- 1.3.6.1.4.1.11001.1.9.1.17
		gscBeamAccessPdtchAssignTimeout OBJECT-TYPE
			SYNTAX Unsigned32
			MAX-ACCESS read-create
			STATUS current
			DESCRIPTION
				"Description."
			::= { gscBeamAccessEntry 17 }

		
		-- 1.3.6.1.4.1.11001.1.9.1.18
		gscBeamAccessPacketRqTimeout OBJECT-TYPE
			SYNTAX Unsigned32
			MAX-ACCESS read-create
			STATUS current
			DESCRIPTION
				"Description."
			::= { gscBeamAccessEntry 18 }

		
		-- 1.3.6.1.4.1.11001.1.9.1.19
		gscBeamAccessReportTime OBJECT-TYPE
			SYNTAX Unsigned32
			MAX-ACCESS read-create
			STATUS current
			DESCRIPTION
				"Description."
			::= { gscBeamAccessEntry 19 }

		
		-- 1.3.6.1.4.1.11001.1.9.1.20
		gscBeamAccessRowstatus OBJECT-TYPE
			SYNTAX INTEGER
				{
				active(1),
				notInservice(2),
				notReady(3),
				createAndGo(4),
				createAndWait(5),
				destory(6)
				}
			MAX-ACCESS read-create
			STATUS current
			DESCRIPTION
				"Description."
			::= { gscBeamAccessEntry 20 }

		
		-- 1.3.6.1.4.1.11001.1.10
		gscBeamCcchTable OBJECT-TYPE
			SYNTAX SEQUENCE OF GscBeamCcchEntry
			MAX-ACCESS not-accessible
			STATUS current
			DESCRIPTION
				"Description."
			::= { gssConfigInfo 10 }

		
		-- 1.3.6.1.4.1.11001.1.10.1
		gscBeamCcchEntry OBJECT-TYPE
			SYNTAX GscBeamCcchEntry
			MAX-ACCESS not-accessible
			STATUS current
			DESCRIPTION
				"Description."
			INDEX { gscCcchIndex }
			::= { gscBeamCcchTable 1 }

		
		GscBeamCcchEntry ::=
			SEQUENCE { 
				gscCcchIndex
					Unsigned32,
				gscCcchVersionID
					OCTET STRING,
				gscCcchAssignTime
					Unsigned32,
				gscCcchBeamId
					Unsigned32,
				gscCcchFrameOffset
					Unsigned32,
				gscCcchBeamUpPowerLimit
					OCTET STRING,
				gscCcchBeamDownPowerLimit
					OCTET STRING,
				gscCcchCarrFreq
					OCTET STRING,
				gscCcchCarrUpPowerLimit
					OCTET STRING,
				gscCcchCarrDownPowerLimit
					OCTET STRING,
				gscCcchCarrDirection
					OCTET STRING,
				gscCcchCarrSlotNo
					OCTET STRING,
				gscCcchCarrSlotLen
					OCTET STRING,
				gscCcchCncarrType
					OCTET STRING,
				gscCcchLogicChannelType
					OCTET STRING,
				gscCcchLogicChannelConfig
					OCTET STRING,
				gscCcchRowStatus
					INTEGER
			 }

		-- 1.3.6.1.4.1.11001.1.10.1.1
		gscCcchIndex OBJECT-TYPE
			SYNTAX Unsigned32 (1..65532)
			MAX-ACCESS not-accessible
			STATUS current
			DESCRIPTION
				"Description."
			::= { gscBeamCcchEntry 1 }

		
		-- 1.3.6.1.4.1.11001.1.10.1.2
		gscCcchVersionID OBJECT-TYPE
			SYNTAX OCTET STRING
			MAX-ACCESS read-create
			STATUS current
			DESCRIPTION
				"Description."
			::= { gscBeamCcchEntry 2 }

		
		-- 1.3.6.1.4.1.11001.1.10.1.3
		gscCcchAssignTime OBJECT-TYPE
			SYNTAX Unsigned32
			MAX-ACCESS read-create
			STATUS current
			DESCRIPTION
				"Description."
			::= { gscBeamCcchEntry 3 }

		
		-- 1.3.6.1.4.1.11001.1.10.1.4
		gscCcchBeamId OBJECT-TYPE
			SYNTAX Unsigned32
			MAX-ACCESS read-create
			STATUS current
			DESCRIPTION
				"Description."
			::= { gscBeamCcchEntry 4 }

		
		-- 1.3.6.1.4.1.11001.1.10.1.5
		gscCcchFrameOffset OBJECT-TYPE
			SYNTAX Unsigned32
			MAX-ACCESS read-create
			STATUS current
			DESCRIPTION
				"Description."
			::= { gscBeamCcchEntry 5 }

		
		-- 1.3.6.1.4.1.11001.1.10.1.6
		gscCcchBeamUpPowerLimit OBJECT-TYPE
			SYNTAX OCTET STRING
			MAX-ACCESS read-create
			STATUS current
			DESCRIPTION
				"Description."
			::= { gscBeamCcchEntry 6 }

		
		-- 1.3.6.1.4.1.11001.1.10.1.7
		gscCcchBeamDownPowerLimit OBJECT-TYPE
			SYNTAX OCTET STRING
			MAX-ACCESS read-create
			STATUS current
			DESCRIPTION
				"Description."
			::= { gscBeamCcchEntry 7 }

		
		-- 1.3.6.1.4.1.11001.1.10.1.8
		gscCcchCarrFreq OBJECT-TYPE
			SYNTAX OCTET STRING
			MAX-ACCESS read-create
			STATUS current
			DESCRIPTION
				"Description."
			::= { gscBeamCcchEntry 8 }

		
		-- 1.3.6.1.4.1.11001.1.10.1.9
		gscCcchCarrUpPowerLimit OBJECT-TYPE
			SYNTAX OCTET STRING
			MAX-ACCESS read-create
			STATUS current
			DESCRIPTION
				"Description."
			::= { gscBeamCcchEntry 9 }

		
		-- 1.3.6.1.4.1.11001.1.10.1.10
		gscCcchCarrDownPowerLimit OBJECT-TYPE
			SYNTAX OCTET STRING
			MAX-ACCESS read-create
			STATUS current
			DESCRIPTION
				"Description."
			::= { gscBeamCcchEntry 10 }

		
		-- 1.3.6.1.4.1.11001.1.10.1.11
		gscCcchCarrDirection OBJECT-TYPE
			SYNTAX OCTET STRING
			MAX-ACCESS read-create
			STATUS current
			DESCRIPTION
				"Description."
			::= { gscBeamCcchEntry 11 }

		
		-- 1.3.6.1.4.1.11001.1.10.1.12
		gscCcchCarrSlotNo OBJECT-TYPE
			SYNTAX OCTET STRING
			MAX-ACCESS read-create
			STATUS current
			DESCRIPTION
				"Description."
			::= { gscBeamCcchEntry 12 }

		
		-- 1.3.6.1.4.1.11001.1.10.1.13
		gscCcchCarrSlotLen OBJECT-TYPE
			SYNTAX OCTET STRING
			MAX-ACCESS read-create
			STATUS current
			DESCRIPTION
				"Description."
			::= { gscBeamCcchEntry 13 }

		
		-- 1.3.6.1.4.1.11001.1.10.1.14
		gscCcchCncarrType OBJECT-TYPE
			SYNTAX OCTET STRING
			MAX-ACCESS read-create
			STATUS current
			DESCRIPTION
				"Description."
			::= { gscBeamCcchEntry 14 }

		
		-- 1.3.6.1.4.1.11001.1.10.1.15
		gscCcchLogicChannelType OBJECT-TYPE
			SYNTAX OCTET STRING
			MAX-ACCESS read-create
			STATUS current
			DESCRIPTION
				"Description."
			::= { gscBeamCcchEntry 15 }

		
		-- 1.3.6.1.4.1.11001.1.10.1.16
		gscCcchLogicChannelConfig OBJECT-TYPE
			SYNTAX OCTET STRING
			MAX-ACCESS read-create
			STATUS current
			DESCRIPTION
				"Description."
			::= { gscBeamCcchEntry 16 }

		
		-- 1.3.6.1.4.1.11001.1.10.1.17
		gscCcchRowStatus OBJECT-TYPE
			SYNTAX INTEGER
				{
				active(1),
				notInservice(2),
				notReady(3),
				createAndGo(4),
				createAndWait(5),
				destroy(6)
				}
			MAX-ACCESS read-create
			STATUS current
			DESCRIPTION
				"Description."
			::= { gscBeamCcchEntry 17 }

		
		-- 1.3.6.1.4.1.11001.1.11
		gscBeamTchTable OBJECT-TYPE
			SYNTAX SEQUENCE OF GscBeamTchEntry
			MAX-ACCESS not-accessible
			STATUS current
			DESCRIPTION
				"Description."
			::= { gssConfigInfo 11 }

		
		-- 1.3.6.1.4.1.11001.1.11.1
		gscBeamTchEntry OBJECT-TYPE
			SYNTAX GscBeamTchEntry
			MAX-ACCESS not-accessible
			STATUS current
			DESCRIPTION
				"Description."
			INDEX { gscTchIndex }
			::= { gscBeamTchTable 1 }

		
		GscBeamTchEntry ::=
			SEQUENCE { 
				gscTchIndex
					Unsigned32,
				gscTchAssignTime
					Unsigned32,
				gscTchVersionID
					OCTET STRING,
				gscTchBeamId
					Unsigned32,
				gscTchFrameOffset
					Unsigned32,
				gscTchBeamUpPowerLimit
					OCTET STRING,
				gscTchBeamDownPowerLimit
					OCTET STRING,
				gscTchCarrAllocation
					OCTET STRING,
				gscTchCarrDirection
					OCTET STRING,
				gscTchCarrUpPowerLimit
					OCTET STRING,
				gscTchCarrDownPowerLimit
					OCTET STRING,
				gscTchCSPSFlag
					OCTET STRING,
				gscTchCarrSlot
					OCTET STRING,
				gscTchRowStatus
					INTEGER
			 }

		-- 1.3.6.1.4.1.11001.1.11.1.1
		gscTchIndex OBJECT-TYPE
			SYNTAX Unsigned32 (1..65532)
			MAX-ACCESS not-accessible
			STATUS current
			DESCRIPTION
				"Description."
			::= { gscBeamTchEntry 1 }

		
		-- 1.3.6.1.4.1.11001.1.11.1.2
		gscTchAssignTime OBJECT-TYPE
			SYNTAX Unsigned32
			MAX-ACCESS read-create
			STATUS current
			DESCRIPTION
				"Description."
			::= { gscBeamTchEntry 2 }

		
		-- 1.3.6.1.4.1.11001.1.11.1.3
		gscTchVersionID OBJECT-TYPE
			SYNTAX OCTET STRING
			MAX-ACCESS read-create
			STATUS current
			DESCRIPTION
				"Description."
			::= { gscBeamTchEntry 3 }

		
		-- 1.3.6.1.4.1.11001.1.11.1.4
		gscTchBeamId OBJECT-TYPE
			SYNTAX Unsigned32
			MAX-ACCESS read-create
			STATUS current
			DESCRIPTION
				"Description."
			::= { gscBeamTchEntry 4 }

		
		-- 1.3.6.1.4.1.11001.1.11.1.5
		gscTchFrameOffset OBJECT-TYPE
			SYNTAX Unsigned32
			MAX-ACCESS read-create
			STATUS current
			DESCRIPTION
				"Description."
			::= { gscBeamTchEntry 5 }

		
		-- 1.3.6.1.4.1.11001.1.11.1.6
		gscTchBeamUpPowerLimit OBJECT-TYPE
			SYNTAX OCTET STRING
			MAX-ACCESS read-create
			STATUS current
			DESCRIPTION
				"Description."
			::= { gscBeamTchEntry 6 }

		
		-- 1.3.6.1.4.1.11001.1.11.1.7
		gscTchBeamDownPowerLimit OBJECT-TYPE
			SYNTAX OCTET STRING
			MAX-ACCESS read-create
			STATUS current
			DESCRIPTION
				"Description."
			::= { gscBeamTchEntry 7 }

		
		-- 1.3.6.1.4.1.11001.1.11.1.8
		gscTchCarrAllocation OBJECT-TYPE
			SYNTAX OCTET STRING
			MAX-ACCESS read-create
			STATUS current
			DESCRIPTION
				"Description."
			::= { gscBeamTchEntry 8 }

		
		-- 1.3.6.1.4.1.11001.1.11.1.9
		gscTchCarrDirection OBJECT-TYPE
			SYNTAX OCTET STRING
			MAX-ACCESS read-create
			STATUS current
			DESCRIPTION
				"Description."
			::= { gscBeamTchEntry 9 }

		
		-- 1.3.6.1.4.1.11001.1.11.1.10
		gscTchCarrUpPowerLimit OBJECT-TYPE
			SYNTAX OCTET STRING
			MAX-ACCESS read-create
			STATUS current
			DESCRIPTION
				"Description."
			::= { gscBeamTchEntry 10 }

		
		-- 1.3.6.1.4.1.11001.1.11.1.11
		gscTchCarrDownPowerLimit OBJECT-TYPE
			SYNTAX OCTET STRING
			MAX-ACCESS read-create
			STATUS current
			DESCRIPTION
				"Description."
			::= { gscBeamTchEntry 11 }

		
		-- 1.3.6.1.4.1.11001.1.11.1.12
		gscTchCSPSFlag OBJECT-TYPE
			SYNTAX OCTET STRING
			MAX-ACCESS read-create
			STATUS current
			DESCRIPTION
				"Description."
			::= { gscBeamTchEntry 12 }

		
		-- 1.3.6.1.4.1.11001.1.11.1.13
		gscTchCarrSlot OBJECT-TYPE
			SYNTAX OCTET STRING
			MAX-ACCESS read-create
			STATUS current
			DESCRIPTION
				"Description."
			::= { gscBeamTchEntry 13 }

		
		-- 1.3.6.1.4.1.11001.1.11.1.14
		gscTchRowStatus OBJECT-TYPE
			SYNTAX INTEGER
				{
				active(1),
				notInservice(2),
				notReady(3),
				createAndGo(4),
				createAndWait(5),
				destroy(6)
				}
			MAX-ACCESS read-create
			STATUS current
			DESCRIPTION
				"Description."
			::= { gscBeamTchEntry 14 }

		
		-- 1.3.6.1.4.1.11001.1.12
		gscBeamSyncTable OBJECT-TYPE
			SYNTAX SEQUENCE OF GscBeamSyncEntry
			MAX-ACCESS not-accessible
			STATUS current
			DESCRIPTION
				"Description."
			::= { gssConfigInfo 12 }

		
		-- 1.3.6.1.4.1.11001.1.12.1
		gscBeamSyncEntry OBJECT-TYPE
			SYNTAX GscBeamSyncEntry
			MAX-ACCESS not-accessible
			STATUS current
			DESCRIPTION
				"Description."
			INDEX { gscBeamSyncIndex }
			::= { gscBeamSyncTable 1 }

		
		GscBeamSyncEntry ::=
			SEQUENCE { 
				gscBeamSyncIndex
					Unsigned32,
				gscBeamSyncAssignTime
					Unsigned32,
				gscBeamSyncVersionID
					OCTET STRING,
				gscBeamSyncBeamID
					Unsigned32,
				gscBeamSyncCcchFreqNum
					Unsigned32,
				gscBeamSyncSacId
					OCTET STRING,
				gscBeamSyncLacId
					OCTET STRING,
				gscBeamSyncRacId
					Unsigned32,
				gscBeamSyncPlmnMcc
					OCTET STRING,
				gscBeamSyncPlmnMnc
					OCTET STRING,
				gscBeamSyncRowStatus
					INTEGER
			 }

		-- 1.3.6.1.4.1.11001.1.12.1.1
		gscBeamSyncIndex OBJECT-TYPE
			SYNTAX Unsigned32 (1..65532)
			MAX-ACCESS not-accessible
			STATUS current
			DESCRIPTION
				"Description."
			::= { gscBeamSyncEntry 1 }

		
		-- 1.3.6.1.4.1.11001.1.12.1.2
		gscBeamSyncAssignTime OBJECT-TYPE
			SYNTAX Unsigned32
			MAX-ACCESS read-create
			STATUS current
			DESCRIPTION
				"Description."
			::= { gscBeamSyncEntry 2 }

		
		-- 1.3.6.1.4.1.11001.1.12.1.3
		gscBeamSyncVersionID OBJECT-TYPE
			SYNTAX OCTET STRING
			MAX-ACCESS read-create
			STATUS current
			DESCRIPTION
				"Description."
			::= { gscBeamSyncEntry 3 }

		
		-- 1.3.6.1.4.1.11001.1.12.1.4
		gscBeamSyncBeamID OBJECT-TYPE
			SYNTAX Unsigned32
			MAX-ACCESS read-create
			STATUS current
			DESCRIPTION
				"Description."
			::= { gscBeamSyncEntry 4 }

		
		-- 1.3.6.1.4.1.11001.1.12.1.5
		gscBeamSyncCcchFreqNum OBJECT-TYPE
			SYNTAX Unsigned32
			MAX-ACCESS read-create
			STATUS current
			DESCRIPTION
				"Description."
			::= { gscBeamSyncEntry 5 }

		
		-- 1.3.6.1.4.1.11001.1.12.1.6
		gscBeamSyncSacId OBJECT-TYPE
			SYNTAX OCTET STRING
			MAX-ACCESS read-create
			STATUS current
			DESCRIPTION
				"Description."
			::= { gscBeamSyncEntry 6 }

		
		-- 1.3.6.1.4.1.11001.1.12.1.7
		gscBeamSyncLacId OBJECT-TYPE
			SYNTAX OCTET STRING
			MAX-ACCESS read-create
			STATUS current
			DESCRIPTION
				"Description."
			::= { gscBeamSyncEntry 7 }

		
		-- 1.3.6.1.4.1.11001.1.12.1.8
		gscBeamSyncRacId OBJECT-TYPE
			SYNTAX Unsigned32
			MAX-ACCESS read-create
			STATUS current
			DESCRIPTION
				"Description."
			::= { gscBeamSyncEntry 8 }

		
		-- 1.3.6.1.4.1.11001.1.12.1.9
		gscBeamSyncPlmnMcc OBJECT-TYPE
			SYNTAX OCTET STRING
			MAX-ACCESS read-create
			STATUS current
			DESCRIPTION
				"Description."
			::= { gscBeamSyncEntry 9 }

		
		-- 1.3.6.1.4.1.11001.1.12.1.10
		gscBeamSyncPlmnMnc OBJECT-TYPE
			SYNTAX OCTET STRING
			MAX-ACCESS read-create
			STATUS current
			DESCRIPTION
				"Description."
			::= { gscBeamSyncEntry 10 }

		
		-- 1.3.6.1.4.1.11001.1.12.1.11
		gscBeamSyncRowStatus OBJECT-TYPE
			SYNTAX INTEGER
				{
				active(1),
				notInservice(2),
				notReady(3),
				createAndGo(4),
				createAndWait(5),
				destroy(6)
				}
			MAX-ACCESS read-create
			STATUS current
			DESCRIPTION
				"Description."
			::= { gscBeamSyncEntry 11 }

		
		-- 1.3.6.1.4.1.11001.1.13
		gscBeamSysInfo1ATable OBJECT-TYPE
			SYNTAX SEQUENCE OF GscBeamSysInfo1AEntry
			MAX-ACCESS not-accessible
			STATUS current
			DESCRIPTION
				"Description."
			::= { gssConfigInfo 13 }

		
		-- 1.3.6.1.4.1.11001.1.13.1
		gscBeamSysInfo1AEntry OBJECT-TYPE
			SYNTAX GscBeamSysInfo1AEntry
			MAX-ACCESS not-accessible
			STATUS current
			DESCRIPTION
				"Description."
			INDEX { gscSysInfo1AIndex }
			::= { gscBeamSysInfo1ATable 1 }

		
		GscBeamSysInfo1AEntry ::=
			SEQUENCE { 
				gscSysInfo1AIndex
					Unsigned32,
				gscSysInfo1AAssignTime
					Unsigned32,
				gscSysInfo1AVersionID
					OCTET STRING,
				gscSysInfo1ABeamID
					Unsigned32,
				gscSysInfo1ARachControlMaxRetrans
					Unsigned32,
				gscSysInfo1ARachControlAccessClasses
					Unsigned32,
				gscSysInfo1ARachControlCellBarAccess
					Unsigned32,
				gscSysInfo1AMiscInfoClass1SBReselectionHystersis
					Unsigned32,
				gscSysInfo1ALsbchPresent
					Unsigned32,
				gscSysInfo1ARowStatus
					INTEGER
			 }

		-- 1.3.6.1.4.1.11001.1.13.1.1
		gscSysInfo1AIndex OBJECT-TYPE
			SYNTAX Unsigned32 (1..65532)
			MAX-ACCESS not-accessible
			STATUS current
			DESCRIPTION
				"Description."
			::= { gscBeamSysInfo1AEntry 1 }

		
		-- 1.3.6.1.4.1.11001.1.13.1.2
		gscSysInfo1AAssignTime OBJECT-TYPE
			SYNTAX Unsigned32
			MAX-ACCESS read-create
			STATUS current
			DESCRIPTION
				"Description."
			::= { gscBeamSysInfo1AEntry 2 }

		
		-- 1.3.6.1.4.1.11001.1.13.1.3
		gscSysInfo1AVersionID OBJECT-TYPE
			SYNTAX OCTET STRING
			MAX-ACCESS read-create
			STATUS current
			DESCRIPTION
				"Description."
			::= { gscBeamSysInfo1AEntry 3 }

		
		-- 1.3.6.1.4.1.11001.1.13.1.4
		gscSysInfo1ABeamID OBJECT-TYPE
			SYNTAX Unsigned32
			MAX-ACCESS read-create
			STATUS current
			DESCRIPTION
				"Description."
			::= { gscBeamSysInfo1AEntry 4 }

		
		-- 1.3.6.1.4.1.11001.1.13.1.5
		gscSysInfo1ARachControlMaxRetrans OBJECT-TYPE
			SYNTAX Unsigned32
			MAX-ACCESS read-create
			STATUS current
			DESCRIPTION
				"Description."
			::= { gscBeamSysInfo1AEntry 5 }

		
		-- 1.3.6.1.4.1.11001.1.13.1.6
		gscSysInfo1ARachControlAccessClasses OBJECT-TYPE
			SYNTAX Unsigned32
			MAX-ACCESS read-create
			STATUS current
			DESCRIPTION
				"Description."
			::= { gscBeamSysInfo1AEntry 6 }

		
		-- 1.3.6.1.4.1.11001.1.13.1.7
		gscSysInfo1ARachControlCellBarAccess OBJECT-TYPE
			SYNTAX Unsigned32
			MAX-ACCESS read-create
			STATUS current
			DESCRIPTION
				"Description."
			::= { gscBeamSysInfo1AEntry 7 }

		
		-- 1.3.6.1.4.1.11001.1.13.1.8
		gscSysInfo1AMiscInfoClass1SBReselectionHystersis OBJECT-TYPE
			SYNTAX Unsigned32
			MAX-ACCESS read-create
			STATUS current
			DESCRIPTION
				"Description."
			::= { gscBeamSysInfo1AEntry 8 }

		
		-- 1.3.6.1.4.1.11001.1.13.1.9
		gscSysInfo1ALsbchPresent OBJECT-TYPE
			SYNTAX Unsigned32
			MAX-ACCESS read-create
			STATUS current
			DESCRIPTION
				"Description."
			::= { gscBeamSysInfo1AEntry 9 }

		
		-- 1.3.6.1.4.1.11001.1.13.1.10
		gscSysInfo1ARowStatus OBJECT-TYPE
			SYNTAX INTEGER
				{
				active(1),
				notInservice(2),
				notReady(3),
				createAndGo(4),
				createAndWait(5),
				destroy(6)
				}
			MAX-ACCESS read-create
			STATUS current
			DESCRIPTION
				"Description."
			::= { gscBeamSysInfo1AEntry 10 }

		
		-- 1.3.6.1.4.1.11001.1.14
		gscBeamSysInfo2AbisTable OBJECT-TYPE
			SYNTAX SEQUENCE OF GscBeamSysInfo2AbisEntry
			MAX-ACCESS not-accessible
			STATUS current
			DESCRIPTION
				"Description."
			::= { gssConfigInfo 14 }

		
		-- 1.3.6.1.4.1.11001.1.14.1
		gscBeamSysInfo2AbisEntry OBJECT-TYPE
			SYNTAX GscBeamSysInfo2AbisEntry
			MAX-ACCESS not-accessible
			STATUS current
			DESCRIPTION
				"Description."
			INDEX { gscSysInfo2AbisIndex }
			::= { gscBeamSysInfo2AbisTable 1 }

		
		GscBeamSysInfo2AbisEntry ::=
			SEQUENCE { 
				gscSysInfo2AbisIndex
					Unsigned32,
				gscSysInfo2AbisAssignTime
					Unsigned32,
				gscSysInfo2AbisVersionID
					OCTET STRING,
				gscSysInfo2AbisBeamID
					Unsigned32,
				gscSysInfo2AbisSelectionCriterionClass2RXLEVSelectMin
					Unsigned32,
				gscSysInfo2AbisMiscInformationClass2SBSelectionPower
					Unsigned32,
				gscSysInfo2AbisLAIClass2RACHTsOffset
					Unsigned32,
				gscSysInfo2AbisLAIClass2NPageOccurrences
					Unsigned32,
				gscSysInfo2AbisRowStatus
					INTEGER
			 }

		-- 1.3.6.1.4.1.11001.1.14.1.1
		gscSysInfo2AbisIndex OBJECT-TYPE
			SYNTAX Unsigned32 (1..65532)
			MAX-ACCESS not-accessible
			STATUS current
			DESCRIPTION
				"Description."
			::= { gscBeamSysInfo2AbisEntry 1 }

		
		-- 1.3.6.1.4.1.11001.1.14.1.2
		gscSysInfo2AbisAssignTime OBJECT-TYPE
			SYNTAX Unsigned32
			MAX-ACCESS read-create
			STATUS current
			DESCRIPTION
				"Description."
			::= { gscBeamSysInfo2AbisEntry 2 }

		
		-- 1.3.6.1.4.1.11001.1.14.1.3
		gscSysInfo2AbisVersionID OBJECT-TYPE
			SYNTAX OCTET STRING
			MAX-ACCESS read-create
			STATUS current
			DESCRIPTION
				"Description."
			::= { gscBeamSysInfo2AbisEntry 3 }

		
		-- 1.3.6.1.4.1.11001.1.14.1.4
		gscSysInfo2AbisBeamID OBJECT-TYPE
			SYNTAX Unsigned32
			MAX-ACCESS read-create
			STATUS current
			DESCRIPTION
				"Description."
			::= { gscBeamSysInfo2AbisEntry 4 }

		
		-- 1.3.6.1.4.1.11001.1.14.1.5
		gscSysInfo2AbisSelectionCriterionClass2RXLEVSelectMin OBJECT-TYPE
			SYNTAX Unsigned32
			MAX-ACCESS read-create
			STATUS current
			DESCRIPTION
				"Description."
			::= { gscBeamSysInfo2AbisEntry 5 }

		
		-- 1.3.6.1.4.1.11001.1.14.1.6
		gscSysInfo2AbisMiscInformationClass2SBSelectionPower OBJECT-TYPE
			SYNTAX Unsigned32
			MAX-ACCESS read-create
			STATUS current
			DESCRIPTION
				"Description."
			::= { gscBeamSysInfo2AbisEntry 6 }

		
		-- 1.3.6.1.4.1.11001.1.14.1.7
		gscSysInfo2AbisLAIClass2RACHTsOffset OBJECT-TYPE
			SYNTAX Unsigned32
			MAX-ACCESS read-create
			STATUS current
			DESCRIPTION
				"Description."
			::= { gscBeamSysInfo2AbisEntry 7 }

		
		-- 1.3.6.1.4.1.11001.1.14.1.8
		gscSysInfo2AbisLAIClass2NPageOccurrences OBJECT-TYPE
			SYNTAX Unsigned32
			MAX-ACCESS read-create
			STATUS current
			DESCRIPTION
				"Description."
			::= { gscBeamSysInfo2AbisEntry 8 }

		
		-- 1.3.6.1.4.1.11001.1.14.1.9
		gscSysInfo2AbisRowStatus OBJECT-TYPE
			SYNTAX INTEGER
				{
				active(1),
				notInservice(2),
				notReady(3),
				createAndGo(4),
				createAndWait(5),
				destroy(6)
				}
			MAX-ACCESS read-create
			STATUS current
			DESCRIPTION
				"Description."
			::= { gscBeamSysInfo2AbisEntry 9 }

		
		-- 1.3.6.1.4.1.11001.1.15
		gscBeamSysInfo3GbisTable OBJECT-TYPE
			SYNTAX SEQUENCE OF GscBeamSysInfo3GbisEntry
			MAX-ACCESS not-accessible
			STATUS current
			DESCRIPTION
				"Description."
			::= { gssConfigInfo 15 }

		
		-- 1.3.6.1.4.1.11001.1.15.1
		gscBeamSysInfo3GbisEntry OBJECT-TYPE
			SYNTAX GscBeamSysInfo3GbisEntry
			MAX-ACCESS not-accessible
			STATUS current
			DESCRIPTION
				"Description."
			INDEX { gscSysInfo3GbisIndex }
			::= { gscBeamSysInfo3GbisTable 1 }

		
		GscBeamSysInfo3GbisEntry ::=
			SEQUENCE { 
				gscSysInfo3GbisIndex
					Unsigned32,
				gscSysInfo3GbisAssignTime
					Unsigned32,
				gscSysInfo3GbisVersionID
					OCTET STRING,
				gscSysInfo3GbisBeamID
					Unsigned32,
				gscSysInfo3GbisPriorityAccessThreshold
					Unsigned32,
				gscSysInfo3GbisLinkFailureMeasurementInterval
					Unsigned32,
				gscSysInfo3GbisMACForwardTSOffset
					Unsigned32,
				gscSysInfo3GbisMACReturenTSOffset
					Unsigned32,
				gscSysInfo3GbisRowStatus
					INTEGER
			 }

		-- 1.3.6.1.4.1.11001.1.15.1.1
		gscSysInfo3GbisIndex OBJECT-TYPE
			SYNTAX Unsigned32 (1..65532)
			MAX-ACCESS not-accessible
			STATUS current
			DESCRIPTION
				"Description."
			::= { gscBeamSysInfo3GbisEntry 1 }

		
		-- 1.3.6.1.4.1.11001.1.15.1.2
		gscSysInfo3GbisAssignTime OBJECT-TYPE
			SYNTAX Unsigned32
			MAX-ACCESS read-create
			STATUS current
			DESCRIPTION
				"Description."
			::= { gscBeamSysInfo3GbisEntry 2 }

		
		-- 1.3.6.1.4.1.11001.1.15.1.3
		gscSysInfo3GbisVersionID OBJECT-TYPE
			SYNTAX OCTET STRING
			MAX-ACCESS read-create
			STATUS current
			DESCRIPTION
				"Description."
			::= { gscBeamSysInfo3GbisEntry 3 }

		
		-- 1.3.6.1.4.1.11001.1.15.1.4
		gscSysInfo3GbisBeamID OBJECT-TYPE
			SYNTAX Unsigned32
			MAX-ACCESS read-create
			STATUS current
			DESCRIPTION
				"Description."
			::= { gscBeamSysInfo3GbisEntry 4 }

		
		-- 1.3.6.1.4.1.11001.1.15.1.5
		gscSysInfo3GbisPriorityAccessThreshold OBJECT-TYPE
			SYNTAX Unsigned32
			MAX-ACCESS read-create
			STATUS current
			DESCRIPTION
				"Description."
			::= { gscBeamSysInfo3GbisEntry 5 }

		
		-- 1.3.6.1.4.1.11001.1.15.1.6
		gscSysInfo3GbisLinkFailureMeasurementInterval OBJECT-TYPE
			SYNTAX Unsigned32
			MAX-ACCESS read-create
			STATUS current
			DESCRIPTION
				"Description."
			::= { gscBeamSysInfo3GbisEntry 6 }

		
		-- 1.3.6.1.4.1.11001.1.15.1.7
		gscSysInfo3GbisMACForwardTSOffset OBJECT-TYPE
			SYNTAX Unsigned32
			MAX-ACCESS read-create
			STATUS current
			DESCRIPTION
				"Description."
			::= { gscBeamSysInfo3GbisEntry 7 }

		
		-- 1.3.6.1.4.1.11001.1.15.1.8
		gscSysInfo3GbisMACReturenTSOffset OBJECT-TYPE
			SYNTAX Unsigned32
			MAX-ACCESS read-create
			STATUS current
			DESCRIPTION
				"Description."
			::= { gscBeamSysInfo3GbisEntry 8 }

		
		-- 1.3.6.1.4.1.11001.1.15.1.9
		gscSysInfo3GbisRowStatus OBJECT-TYPE
			SYNTAX INTEGER
				{
				active(1),
				notInservice(2),
				notReady(3),
				createAndGo(4),
				createAndWait(5),
				destroy(6)
				}
			MAX-ACCESS read-create
			STATUS current
			DESCRIPTION
				"Description."
			::= { gscBeamSysInfo3GbisEntry 9 }

		
		-- 1.3.6.1.4.1.11001.1.16
		gscBeamSysInfo3ITable OBJECT-TYPE
			SYNTAX SEQUENCE OF GscBeamSysInfo3IEntry
			MAX-ACCESS not-accessible
			STATUS current
			DESCRIPTION
				"Description."
			::= { gssConfigInfo 16 }

		
		-- 1.3.6.1.4.1.11001.1.16.1
		gscBeamSysInfo3IEntry OBJECT-TYPE
			SYNTAX GscBeamSysInfo3IEntry
			MAX-ACCESS not-accessible
			STATUS current
			DESCRIPTION
				"Description."
			INDEX { gscSysInfo3IIndex }
			::= { gscBeamSysInfo3ITable 1 }

		
		GscBeamSysInfo3IEntry ::=
			SEQUENCE { 
				gscSysInfo3IIndex
					Unsigned32,
				gscSysInfo3IAssignTime
					Unsigned32,
				gscSysInfo3IVersionID
					OCTET STRING,
				gscSysInfo3IBeamID
					Unsigned32,
				gscSysInfo3ILAIClass3PauseTimer
					Unsigned32,
				gscSysInfo3ILAIClass3RACHAccessTimer
					Unsigned32,
				gscSysInfo3ILAIClass3AlertTimer
					Unsigned32,
				gscSysInfo3ILAIClass3PagingTimer
					Unsigned32,
				gscSysInfo3IPeriodicLUTimer
					Unsigned32,
				gscSysInfo3IDualModeHoldTimer
					Unsigned32,
				gscSysInfo3IPositionParaRACHPositionTimer
					Unsigned32,
				gscSysInfo3IPositionParaGPSUpdateTimer
					Unsigned32,
				gscSysInfo3IPositionParaGPSUpdateDistance
					Unsigned32,
				gscSysInfo3IPositionParaGPSPositionAge
					Unsigned32,
				gscSysInfo3IPositionParaPageGPSPositionAge
					Unsigned32,
				gscSysInfo3IPositionParaPageResponseCurrentGPS
					Unsigned32,
				gscSysInfo3IPositionParaPositionReportingRequired
					Unsigned32,
				gscSysInfo3IRowStatus
					INTEGER
			 }

		-- 1.3.6.1.4.1.11001.1.16.1.1
		gscSysInfo3IIndex OBJECT-TYPE
			SYNTAX Unsigned32 (1..65532)
			MAX-ACCESS not-accessible
			STATUS current
			DESCRIPTION
				"Description."
			::= { gscBeamSysInfo3IEntry 1 }

		
		-- 1.3.6.1.4.1.11001.1.16.1.2
		gscSysInfo3IAssignTime OBJECT-TYPE
			SYNTAX Unsigned32
			MAX-ACCESS read-create
			STATUS current
			DESCRIPTION
				"Description."
			::= { gscBeamSysInfo3IEntry 2 }

		
		-- 1.3.6.1.4.1.11001.1.16.1.3
		gscSysInfo3IVersionID OBJECT-TYPE
			SYNTAX OCTET STRING
			MAX-ACCESS read-create
			STATUS current
			DESCRIPTION
				"Description."
			::= { gscBeamSysInfo3IEntry 3 }

		
		-- 1.3.6.1.4.1.11001.1.16.1.4
		gscSysInfo3IBeamID OBJECT-TYPE
			SYNTAX Unsigned32
			MAX-ACCESS read-create
			STATUS current
			DESCRIPTION
				"Description."
			::= { gscBeamSysInfo3IEntry 4 }

		
		-- 1.3.6.1.4.1.11001.1.16.1.5
		gscSysInfo3ILAIClass3PauseTimer OBJECT-TYPE
			SYNTAX Unsigned32
			MAX-ACCESS read-create
			STATUS current
			DESCRIPTION
				"Description."
			::= { gscBeamSysInfo3IEntry 5 }

		
		-- 1.3.6.1.4.1.11001.1.16.1.6
		gscSysInfo3ILAIClass3RACHAccessTimer OBJECT-TYPE
			SYNTAX Unsigned32
			MAX-ACCESS read-create
			STATUS current
			DESCRIPTION
				"Description."
			::= { gscBeamSysInfo3IEntry 6 }

		
		-- 1.3.6.1.4.1.11001.1.16.1.7
		gscSysInfo3ILAIClass3AlertTimer OBJECT-TYPE
			SYNTAX Unsigned32
			MAX-ACCESS read-create
			STATUS current
			DESCRIPTION
				"Description."
			::= { gscBeamSysInfo3IEntry 7 }

		
		-- 1.3.6.1.4.1.11001.1.16.1.8
		gscSysInfo3ILAIClass3PagingTimer OBJECT-TYPE
			SYNTAX Unsigned32
			MAX-ACCESS read-create
			STATUS current
			DESCRIPTION
				"Description."
			::= { gscBeamSysInfo3IEntry 8 }

		
		-- 1.3.6.1.4.1.11001.1.16.1.9
		gscSysInfo3IPeriodicLUTimer OBJECT-TYPE
			SYNTAX Unsigned32
			MAX-ACCESS read-create
			STATUS current
			DESCRIPTION
				"Description."
			::= { gscBeamSysInfo3IEntry 9 }

		
		-- 1.3.6.1.4.1.11001.1.16.1.10
		gscSysInfo3IDualModeHoldTimer OBJECT-TYPE
			SYNTAX Unsigned32
			MAX-ACCESS read-create
			STATUS current
			DESCRIPTION
				"Description."
			::= { gscBeamSysInfo3IEntry 10 }

		
		-- 1.3.6.1.4.1.11001.1.16.1.11
		gscSysInfo3IPositionParaRACHPositionTimer OBJECT-TYPE
			SYNTAX Unsigned32
			MAX-ACCESS read-create
			STATUS current
			DESCRIPTION
				"Description."
			::= { gscBeamSysInfo3IEntry 11 }

		
		-- 1.3.6.1.4.1.11001.1.16.1.12
		gscSysInfo3IPositionParaGPSUpdateTimer OBJECT-TYPE
			SYNTAX Unsigned32
			MAX-ACCESS read-create
			STATUS current
			DESCRIPTION
				"Description."
			::= { gscBeamSysInfo3IEntry 12 }

		
		-- 1.3.6.1.4.1.11001.1.16.1.13
		gscSysInfo3IPositionParaGPSUpdateDistance OBJECT-TYPE
			SYNTAX Unsigned32
			MAX-ACCESS read-create
			STATUS current
			DESCRIPTION
				"Description."
			::= { gscBeamSysInfo3IEntry 13 }

		
		-- 1.3.6.1.4.1.11001.1.16.1.14
		gscSysInfo3IPositionParaGPSPositionAge OBJECT-TYPE
			SYNTAX Unsigned32
			MAX-ACCESS read-create
			STATUS current
			DESCRIPTION
				"Description."
			::= { gscBeamSysInfo3IEntry 14 }

		
		-- 1.3.6.1.4.1.11001.1.16.1.15
		gscSysInfo3IPositionParaPageGPSPositionAge OBJECT-TYPE
			SYNTAX Unsigned32
			MAX-ACCESS read-create
			STATUS current
			DESCRIPTION
				"Description."
			::= { gscBeamSysInfo3IEntry 15 }

		
		-- 1.3.6.1.4.1.11001.1.16.1.16
		gscSysInfo3IPositionParaPageResponseCurrentGPS OBJECT-TYPE
			SYNTAX Unsigned32
			MAX-ACCESS read-create
			STATUS current
			DESCRIPTION
				"Description."
			::= { gscBeamSysInfo3IEntry 16 }

		
		-- 1.3.6.1.4.1.11001.1.16.1.17
		gscSysInfo3IPositionParaPositionReportingRequired OBJECT-TYPE
			SYNTAX Unsigned32
			MAX-ACCESS read-create
			STATUS current
			DESCRIPTION
				"Description."
			::= { gscBeamSysInfo3IEntry 17 }

		
		-- 1.3.6.1.4.1.11001.1.16.1.18
		gscSysInfo3IRowStatus OBJECT-TYPE
			SYNTAX INTEGER
				{
				active(1),
				notInservice(2),
				notReady(3),
				createAndGo(4),
				createAndWait(5),
				destroy(6)
				}
			MAX-ACCESS read-create
			STATUS current
			DESCRIPTION
				"Description."
			::= { gscBeamSysInfo3IEntry 18 }

		
		-- 1.3.6.1.4.1.11001.1.17
		gscBeamSysInfo4CTable OBJECT-TYPE
			SYNTAX SEQUENCE OF GscBeamSysInfo4CEntry
			MAX-ACCESS not-accessible
			STATUS current
			DESCRIPTION
				"Description."
			::= { gssConfigInfo 17 }

		
		-- 1.3.6.1.4.1.11001.1.17.1
		gscBeamSysInfo4CEntry OBJECT-TYPE
			SYNTAX GscBeamSysInfo4CEntry
			MAX-ACCESS not-accessible
			STATUS current
			DESCRIPTION
				"Description."
			INDEX { gscSysInfo4CIndex }
			::= { gscBeamSysInfo4CTable 1 }

		
		GscBeamSysInfo4CEntry ::=
			SEQUENCE { 
				gscSysInfo4CIndex
					Unsigned32,
				gscSysInfo4CAssignTime
					Unsigned32,
				gscSysInfo4CVersionID
					OCTET STRING,
				gscSysInfo4CBeamID
					Unsigned32,
				gscSysInfo4CHHTSQT
					Unsigned32,
				gscSysInfo4CHHTDataSQT
					Unsigned32,
				gscSysInfo4CVTSQT
					Unsigned32,
				gscSysInfo4CVTDataSQT
					Unsigned32,
				gscSysInfo4CFTSQT
					Unsigned32,
				gscSysInfo4CFTDataSQT
					Unsigned32,
				gscSysInfo4CPANinit
					Unsigned32,
				gscSysInfo4CPANmin
					Unsigned32,
				gscSysInfo4CPANmax
					Unsigned32,
				gscSysInfo4CGainUp
					Unsigned32,
				gscSysInfo4CGainDn
					Unsigned32,
				gscSysInfo4COlthresh
					Unsigned32,
				gscSysInfo4COlupGain
					Unsigned32,
				gscSysInfo4COldnGain
					Unsigned32,
				gscSysInfo4CVarUp
					Unsigned32,
				gscSysInfo4CVarDn
					Unsigned32,
				gscSysInfo4CSQIfactor
					Unsigned32,
				gscSysInfo4CMestep
					Unsigned32,
				gscSysInfo4CLQIn1
					Unsigned32,
				gscSysInfo4CLQIn2
					Unsigned32,
				gscSysInfo4CRowStatus
					INTEGER
			 }

		-- 1.3.6.1.4.1.11001.1.17.1.1
		gscSysInfo4CIndex OBJECT-TYPE
			SYNTAX Unsigned32 (1..65532)
			MAX-ACCESS not-accessible
			STATUS current
			DESCRIPTION
				"Description."
			::= { gscBeamSysInfo4CEntry 1 }

		
		-- 1.3.6.1.4.1.11001.1.17.1.2
		gscSysInfo4CAssignTime OBJECT-TYPE
			SYNTAX Unsigned32
			MAX-ACCESS read-create
			STATUS current
			DESCRIPTION
				"Description."
			::= { gscBeamSysInfo4CEntry 2 }

		
		-- 1.3.6.1.4.1.11001.1.17.1.3
		gscSysInfo4CVersionID OBJECT-TYPE
			SYNTAX OCTET STRING
			MAX-ACCESS read-create
			STATUS current
			DESCRIPTION
				"Description."
			::= { gscBeamSysInfo4CEntry 3 }

		
		-- 1.3.6.1.4.1.11001.1.17.1.4
		gscSysInfo4CBeamID OBJECT-TYPE
			SYNTAX Unsigned32
			MAX-ACCESS read-create
			STATUS current
			DESCRIPTION
				"Description."
			::= { gscBeamSysInfo4CEntry 4 }

		
		-- 1.3.6.1.4.1.11001.1.17.1.5
		gscSysInfo4CHHTSQT OBJECT-TYPE
			SYNTAX Unsigned32
			MAX-ACCESS read-create
			STATUS current
			DESCRIPTION
				"Description."
			::= { gscBeamSysInfo4CEntry 5 }

		
		-- 1.3.6.1.4.1.11001.1.17.1.6
		gscSysInfo4CHHTDataSQT OBJECT-TYPE
			SYNTAX Unsigned32
			MAX-ACCESS read-create
			STATUS current
			DESCRIPTION
				"Description."
			::= { gscBeamSysInfo4CEntry 6 }

		
		-- 1.3.6.1.4.1.11001.1.17.1.7
		gscSysInfo4CVTSQT OBJECT-TYPE
			SYNTAX Unsigned32
			MAX-ACCESS read-create
			STATUS current
			DESCRIPTION
				"Description."
			::= { gscBeamSysInfo4CEntry 7 }

		
		-- 1.3.6.1.4.1.11001.1.17.1.8
		gscSysInfo4CVTDataSQT OBJECT-TYPE
			SYNTAX Unsigned32
			MAX-ACCESS read-create
			STATUS current
			DESCRIPTION
				"Description."
			::= { gscBeamSysInfo4CEntry 8 }

		
		-- 1.3.6.1.4.1.11001.1.17.1.9
		gscSysInfo4CFTSQT OBJECT-TYPE
			SYNTAX Unsigned32
			MAX-ACCESS read-create
			STATUS current
			DESCRIPTION
				"Description."
			::= { gscBeamSysInfo4CEntry 9 }

		
		-- 1.3.6.1.4.1.11001.1.17.1.10
		gscSysInfo4CFTDataSQT OBJECT-TYPE
			SYNTAX Unsigned32
			MAX-ACCESS read-create
			STATUS current
			DESCRIPTION
				"Description."
			::= { gscBeamSysInfo4CEntry 10 }

		
		-- 1.3.6.1.4.1.11001.1.17.1.11
		gscSysInfo4CPANinit OBJECT-TYPE
			SYNTAX Unsigned32
			MAX-ACCESS read-create
			STATUS current
			DESCRIPTION
				"Description."
			::= { gscBeamSysInfo4CEntry 11 }

		
		-- 1.3.6.1.4.1.11001.1.17.1.12
		gscSysInfo4CPANmin OBJECT-TYPE
			SYNTAX Unsigned32
			MAX-ACCESS read-create
			STATUS current
			DESCRIPTION
				"Description."
			::= { gscBeamSysInfo4CEntry 12 }

		
		-- 1.3.6.1.4.1.11001.1.17.1.13
		gscSysInfo4CPANmax OBJECT-TYPE
			SYNTAX Unsigned32
			MAX-ACCESS read-create
			STATUS current
			DESCRIPTION
				"Description."
			::= { gscBeamSysInfo4CEntry 13 }

		
		-- 1.3.6.1.4.1.11001.1.17.1.14
		gscSysInfo4CGainUp OBJECT-TYPE
			SYNTAX Unsigned32
			MAX-ACCESS read-create
			STATUS current
			DESCRIPTION
				"Description."
			::= { gscBeamSysInfo4CEntry 14 }

		
		-- 1.3.6.1.4.1.11001.1.17.1.15
		gscSysInfo4CGainDn OBJECT-TYPE
			SYNTAX Unsigned32
			MAX-ACCESS read-create
			STATUS current
			DESCRIPTION
				"Description."
			::= { gscBeamSysInfo4CEntry 15 }

		
		-- 1.3.6.1.4.1.11001.1.17.1.16
		gscSysInfo4COlthresh OBJECT-TYPE
			SYNTAX Unsigned32
			MAX-ACCESS read-create
			STATUS current
			DESCRIPTION
				"Description."
			::= { gscBeamSysInfo4CEntry 16 }

		
		-- 1.3.6.1.4.1.11001.1.17.1.17
		gscSysInfo4COlupGain OBJECT-TYPE
			SYNTAX Unsigned32
			MAX-ACCESS read-create
			STATUS current
			DESCRIPTION
				"Description."
			::= { gscBeamSysInfo4CEntry 17 }

		
		-- 1.3.6.1.4.1.11001.1.17.1.18
		gscSysInfo4COldnGain OBJECT-TYPE
			SYNTAX Unsigned32
			MAX-ACCESS read-create
			STATUS current
			DESCRIPTION
				"Description."
			::= { gscBeamSysInfo4CEntry 18 }

		
		-- 1.3.6.1.4.1.11001.1.17.1.19
		gscSysInfo4CVarUp OBJECT-TYPE
			SYNTAX Unsigned32
			MAX-ACCESS read-create
			STATUS current
			DESCRIPTION
				"Description."
			::= { gscBeamSysInfo4CEntry 19 }

		
		-- 1.3.6.1.4.1.11001.1.17.1.20
		gscSysInfo4CVarDn OBJECT-TYPE
			SYNTAX Unsigned32
			MAX-ACCESS read-create
			STATUS current
			DESCRIPTION
				"Description."
			::= { gscBeamSysInfo4CEntry 20 }

		
		-- 1.3.6.1.4.1.11001.1.17.1.21
		gscSysInfo4CSQIfactor OBJECT-TYPE
			SYNTAX Unsigned32
			MAX-ACCESS read-create
			STATUS current
			DESCRIPTION
				"Description."
			::= { gscBeamSysInfo4CEntry 21 }

		
		-- 1.3.6.1.4.1.11001.1.17.1.22
		gscSysInfo4CMestep OBJECT-TYPE
			SYNTAX Unsigned32
			MAX-ACCESS read-create
			STATUS current
			DESCRIPTION
				"Description."
			::= { gscBeamSysInfo4CEntry 22 }

		
		-- 1.3.6.1.4.1.11001.1.17.1.23
		gscSysInfo4CLQIn1 OBJECT-TYPE
			SYNTAX Unsigned32
			MAX-ACCESS read-create
			STATUS current
			DESCRIPTION
				"Description."
			::= { gscBeamSysInfo4CEntry 23 }

		
		-- 1.3.6.1.4.1.11001.1.17.1.24
		gscSysInfo4CLQIn2 OBJECT-TYPE
			SYNTAX Unsigned32
			MAX-ACCESS read-create
			STATUS current
			DESCRIPTION
				"Description."
			::= { gscBeamSysInfo4CEntry 24 }

		
		-- 1.3.6.1.4.1.11001.1.17.1.25
		gscSysInfo4CRowStatus OBJECT-TYPE
			SYNTAX INTEGER
				{
				active(1),
				notInservice(2),
				notReady(3),
				createAndGo(4),
				createAndWait(5),
				destroy(6)
				}
			MAX-ACCESS read-create
			STATUS current
			DESCRIPTION
				"Description."
			::= { gscBeamSysInfo4CEntry 25 }

		
		-- 1.3.6.1.4.1.11001.1.18
		gscBeamSysInfoOthersTable OBJECT-TYPE
			SYNTAX SEQUENCE OF GscBeamSysInfoOthersEntry
			MAX-ACCESS not-accessible
			STATUS current
			DESCRIPTION
				"Description."
			::= { gssConfigInfo 18 }

		
		-- 1.3.6.1.4.1.11001.1.18.1
		gscBeamSysInfoOthersEntry OBJECT-TYPE
			SYNTAX GscBeamSysInfoOthersEntry
			MAX-ACCESS not-accessible
			STATUS current
			DESCRIPTION
				"Description."
			INDEX { gscSysInfoOthersIndex }
			::= { gscBeamSysInfoOthersTable 1 }

		
		GscBeamSysInfoOthersEntry ::=
			SEQUENCE { 
				gscSysInfoOthersIndex
					Unsigned32,
				gscSysInfoOthersAssignTime
					Unsigned32,
				gscSysInfoOthersVersionID
					OCTET STRING,
				gscSysInfoOthersBeamID
					Unsigned32,
				gscSysInfoRandomizationPeriod
					Unsigned32,
				gscSysInfo3ASBReselectionTimer
					Unsigned32,
				gscSysInfo3BbisSBMask
					Unsigned32,
				gscSysInfo3BbisImplicitDetachTimer
					Unsigned32,
				gscSysInfo4ARadioLinkTimeout
					Unsigned32,
				gscSysInfoOthersRowStatus
					INTEGER
			 }

		-- 1.3.6.1.4.1.11001.1.18.1.1
		gscSysInfoOthersIndex OBJECT-TYPE
			SYNTAX Unsigned32 (1..65532)
			MAX-ACCESS not-accessible
			STATUS current
			DESCRIPTION
				"Description."
			::= { gscBeamSysInfoOthersEntry 1 }

		
		-- 1.3.6.1.4.1.11001.1.18.1.2
		gscSysInfoOthersAssignTime OBJECT-TYPE
			SYNTAX Unsigned32
			MAX-ACCESS read-create
			STATUS current
			DESCRIPTION
				"Description."
			::= { gscBeamSysInfoOthersEntry 2 }

		
		-- 1.3.6.1.4.1.11001.1.18.1.3
		gscSysInfoOthersVersionID OBJECT-TYPE
			SYNTAX OCTET STRING
			MAX-ACCESS read-create
			STATUS current
			DESCRIPTION
				"Description."
			::= { gscBeamSysInfoOthersEntry 3 }

		
		-- 1.3.6.1.4.1.11001.1.18.1.4
		gscSysInfoOthersBeamID OBJECT-TYPE
			SYNTAX Unsigned32
			MAX-ACCESS read-create
			STATUS current
			DESCRIPTION
				"Description."
			::= { gscBeamSysInfoOthersEntry 4 }

		
		-- 1.3.6.1.4.1.11001.1.18.1.5
		gscSysInfoRandomizationPeriod OBJECT-TYPE
			SYNTAX Unsigned32
			MAX-ACCESS read-create
			STATUS current
			DESCRIPTION
				"Description."
			::= { gscBeamSysInfoOthersEntry 5 }

		
		-- 1.3.6.1.4.1.11001.1.18.1.6
		gscSysInfo3ASBReselectionTimer OBJECT-TYPE
			SYNTAX Unsigned32
			MAX-ACCESS read-create
			STATUS current
			DESCRIPTION
				"Description."
			::= { gscBeamSysInfoOthersEntry 6 }

		
		-- 1.3.6.1.4.1.11001.1.18.1.7
		gscSysInfo3BbisSBMask OBJECT-TYPE
			SYNTAX Unsigned32
			MAX-ACCESS read-create
			STATUS current
			DESCRIPTION
				"Description."
			::= { gscBeamSysInfoOthersEntry 7 }

		
		-- 1.3.6.1.4.1.11001.1.18.1.8
		gscSysInfo3BbisImplicitDetachTimer OBJECT-TYPE
			SYNTAX Unsigned32
			MAX-ACCESS read-create
			STATUS current
			DESCRIPTION
				"Description."
			::= { gscBeamSysInfoOthersEntry 8 }

		
		-- 1.3.6.1.4.1.11001.1.18.1.9
		gscSysInfo4ARadioLinkTimeout OBJECT-TYPE
			SYNTAX Unsigned32
			MAX-ACCESS read-create
			STATUS current
			DESCRIPTION
				"Description."
			::= { gscBeamSysInfoOthersEntry 9 }

		
		-- 1.3.6.1.4.1.11001.1.18.1.10
		gscSysInfoOthersRowStatus OBJECT-TYPE
			SYNTAX INTEGER
				{
				active(1),
				notInservice(2),
				notReady(3),
				createAndGo(4),
				createAndWait(5),
				destroy(6)
				}
			MAX-ACCESS read-create
			STATUS current
			DESCRIPTION
				"Description."
			::= { gscBeamSysInfoOthersEntry 10 }

		
--  Node definitions
-- 
-- Node definitions
-- 
-- 1.3.6.1.4.1.1.1
-- 1.3.6.1.4.1.1.1
		-- 1.3.6.1.4.1.11001.2
		grmTotalInfo OBJECT IDENTIFIER ::= { grmAgentxMIB 2 }

		
		-- 1.3.6.1.4.1.11001.2.1
		grmSoftwareStatus OBJECT-TYPE
			SYNTAX INTEGER
				{
				alive(1),
				dead(2),
				unknown(3)
				}
			MAX-ACCESS read-only
			STATUS current
			DESCRIPTION
				"Description."
			::= { grmTotalInfo 1 }

		
		-- 1.3.6.1.4.1.11001.2.2
		grmPortSctp OBJECT-TYPE
			SYNTAX Unsigned32
			MAX-ACCESS read-write
			STATUS current
			DESCRIPTION
				"Description."
			::= { grmTotalInfo 2 }

		
		-- 1.3.6.1.4.1.11001.2.3
		grmCoOpcIp OBJECT-TYPE
			SYNTAX IpAddress
			MAX-ACCESS read-write
			STATUS current
			DESCRIPTION
				"Description."
			::= { grmTotalInfo 3 }

		
		-- 1.3.6.1.4.1.11001.2.4
		grmCoOpcPort OBJECT-TYPE
			SYNTAX Unsigned32
			MAX-ACCESS read-write
			STATUS current
			DESCRIPTION
				"Description."
			::= { grmTotalInfo 4 }

		
		-- 1.3.6.1.4.1.11001.2.5
		grmCoGSCInfoTable OBJECT-TYPE
			SYNTAX SEQUENCE OF GrmCoGSCInfoEntry
			MAX-ACCESS not-accessible
			STATUS current
			DESCRIPTION
				"Description."
			::= { grmTotalInfo 5 }

		
		-- 1.3.6.1.4.1.11001.2.5.1
		grmCoGSCInfoEntry OBJECT-TYPE
			SYNTAX GrmCoGSCInfoEntry
			MAX-ACCESS not-accessible
			STATUS current
			DESCRIPTION
				"Description."
			INDEX { grmCoGSCIndex }
			::= { grmCoGSCInfoTable 1 }

		
		GrmCoGSCInfoEntry ::=
			SEQUENCE { 
				grmCoGSCIndex
					Unsigned32,
				grmCoGSCIp
					IpAddress,
				grmCoGSCPort
					Unsigned32,
				grmCoGSCRowStatus
					INTEGER
			 }

		-- 1.3.6.1.4.1.11001.2.5.1.1
		grmCoGSCIndex OBJECT-TYPE
			SYNTAX Unsigned32 (1..65532)
			MAX-ACCESS not-accessible
			STATUS current
			DESCRIPTION
				"Description."
			::= { grmCoGSCInfoEntry 1 }

		
		-- 1.3.6.1.4.1.11001.2.5.1.2
		grmCoGSCIp OBJECT-TYPE
			SYNTAX IpAddress
			MAX-ACCESS read-create
			STATUS current
			DESCRIPTION
				"Description."
			::= { grmCoGSCInfoEntry 2 }

		
		-- 1.3.6.1.4.1.11001.2.5.1.3
		grmCoGSCPort OBJECT-TYPE
			SYNTAX Unsigned32
			MAX-ACCESS read-create
			STATUS current
			DESCRIPTION
				"Description."
			::= { grmCoGSCInfoEntry 3 }

		
		-- 1.3.6.1.4.1.11001.2.5.1.4
		grmCoGSCRowStatus OBJECT-TYPE
			SYNTAX INTEGER
				{
				active(1),
				notInservice(2),
				notReady(3),
				createAndGo(4),
				createAndWait(5),
				destroy(6)
				}
			MAX-ACCESS read-create
			STATUS current
			DESCRIPTION
				"Description."
			::= { grmCoGSCInfoEntry 4 }

		
--   1.3.6.1.4.1.1.4
-- 1.3.6.1.4.1.1.4
		-- 1.3.6.1.4.1.11001.3
		alarm OBJECT IDENTIFIER ::= { grmAgentxMIB 3 }

		
--   1.3.6.1.4.1.1.4.1
-- 1.3.6.1.4.1.1.4.1
		-- 1.3.6.1.4.1.11001.3.1
		currentAlarmTable OBJECT-TYPE
			SYNTAX SEQUENCE OF CurrentAlarmEntry
			MAX-ACCESS not-accessible
			STATUS current
			DESCRIPTION
				"store the current alarms"
			::= { alarm 1 }

		
--   1.3.6.1.4.1.1.4.1.1
-- 1.3.6.1.4.1.1.4.1.1
		-- 1.3.6.1.4.1.11001.3.1.1
		currentAlarmEntry OBJECT-TYPE
			SYNTAX CurrentAlarmEntry
			MAX-ACCESS not-accessible
			STATUS current
			DESCRIPTION
				"Description."
			INDEX { currentAlarmIndex }
			::= { currentAlarmTable 1 }

		
		CurrentAlarmEntry ::=
			SEQUENCE { 
				currentAlarmIndex
					Unsigned32,
				currentAlarmName
					OCTET STRING,
				currentAlarmNotifyOID
					OBJECT IDENTIFIER,
				currentAlarmRaisedTime
					TimeTicks,
				currentAlarmChangedTime
					TimeTicks,
				currentAlarmEventType
					INTEGER,
				currentAlarmProbableCause
					OCTET STRING,
				currentAlarmSpecificProblem
					OCTET STRING,
				currentAlarmPerceivedSeverity
					INTEGER,
				currentAlarmReportingMechanism
					INTEGER,
				currentAlarmDeviceID
					Unsigned32,
				currentAlarmDeviceType
					INTEGER,
				currentAlarmDeviceAddr
					IpAddress,
				currentAlarmAddtionalText
					OCTET STRING,
				currentAlarmProposeRepairAction
					OCTET STRING,
				currentAlarmClearAction
					INTEGER
			 }

--   1.3.6.1.4.1.1.4.1.1.1
-- 1.3.6.1.4.1.1.4.1.1.1
		-- 1.3.6.1.4.1.11001.3.1.1.1
		currentAlarmIndex OBJECT-TYPE
			SYNTAX Unsigned32 (1..65534)
			MAX-ACCESS not-accessible
			STATUS current
			DESCRIPTION
				"Description."
			::= { currentAlarmEntry 1 }

		
--   1.3.6.1.4.1.1.4.1.1.2
-- 1.3.6.1.4.1.1.4.1.1.2
		-- 1.3.6.1.4.1.11001.3.1.1.2
		currentAlarmName OBJECT-TYPE
			SYNTAX OCTET STRING
			MAX-ACCESS read-only
			STATUS current
			DESCRIPTION
				"Description."
			::= { currentAlarmEntry 2 }

		
--  1.3.6.1.4.1.1.4.1.1.3
		-- 1.3.6.1.4.1.11001.3.1.1.3
		currentAlarmNotifyOID OBJECT-TYPE
			SYNTAX OBJECT IDENTIFIER
			MAX-ACCESS read-only
			STATUS current
			DESCRIPTION
				"Description."
			::= { currentAlarmEntry 3 }

		
--   1.3.6.1.4.1.1.4.1.1.3
-- 1.3.6.1.4.1.1.4.1.1.4
		-- 1.3.6.1.4.1.11001.3.1.1.4
		currentAlarmRaisedTime OBJECT-TYPE
			SYNTAX TimeTicks
			UNITS "s"
			MAX-ACCESS read-only
			STATUS current
			DESCRIPTION
				"Description."
			::= { currentAlarmEntry 4 }

		
--   1.3.6.1.4.1.1.4.1.1.4
-- 1.3.6.1.4.1.1.4.1.1.5
		-- 1.3.6.1.4.1.11001.3.1.1.5
		currentAlarmChangedTime OBJECT-TYPE
			SYNTAX TimeTicks
			UNITS "s"
			MAX-ACCESS read-only
			STATUS current
			DESCRIPTION
				"Description."
			::= { currentAlarmEntry 5 }

		
--   1.3.6.1.4.1.1.4.1.1.5
-- 1.3.6.1.4.1.1.4.1.1.6
		-- 1.3.6.1.4.1.11001.3.1.1.6
		currentAlarmEventType OBJECT-TYPE
			SYNTAX INTEGER
				{
				communicationAlarm(1),
				deviceAlarm(2),
				dataProcessingAlarm(3),
				qualitySeriveAlarm(4),
				environmentAlarm(5),
				integrityAlarm(6),
				securityAlarm(7),
				timezoneAlarm(8),
				operationAlarm(9),
				physicalAlarm(10)
				}
			MAX-ACCESS read-only
			STATUS current
			DESCRIPTION
				"Description."
			::= { currentAlarmEntry 6 }

		
--   1.3.6.1.4.1.1.4.1.1.6
-- 1.3.6.1.4.1.1.4.1.1.7
		-- 1.3.6.1.4.1.11001.3.1.1.7
		currentAlarmProbableCause OBJECT-TYPE
			SYNTAX OCTET STRING
			MAX-ACCESS read-only
			STATUS current
			DESCRIPTION
				"Description."
			::= { currentAlarmEntry 7 }

		
--   1.3.6.1.4.1.1.4.1.1.7
-- 1.3.6.1.4.1.1.4.1.1.8
		-- 1.3.6.1.4.1.11001.3.1.1.8
		currentAlarmSpecificProblem OBJECT-TYPE
			SYNTAX OCTET STRING
			MAX-ACCESS read-only
			STATUS current
			DESCRIPTION
				"Description."
			::= { currentAlarmEntry 8 }

		
--   1.3.6.1.4.1.1.4.1.1.8
-- 1.3.6.1.4.1.1.4.1.1.9
		-- 1.3.6.1.4.1.11001.3.1.1.9
		currentAlarmPerceivedSeverity OBJECT-TYPE
			SYNTAX INTEGER
				{
				critical(1),
				major(2),
				minor(3),
				warning(4),
				indeterminate(5),
				cleared(6)
				}
			MAX-ACCESS read-only
			STATUS current
			DESCRIPTION
				"Description."
			::= { currentAlarmEntry 9 }

		
--  1.3.6.1.4.1.1.4.1.1.10
		-- 1.3.6.1.4.1.11001.3.1.1.10
		currentAlarmReportingMechanism OBJECT-TYPE
			SYNTAX INTEGER
				{
				expedited(1),
				pending(2),
				logged(3)
				}
			MAX-ACCESS read-only
			STATUS current
			DESCRIPTION
				"Description."
			::= { currentAlarmEntry 10 }

		
--   1.3.6.1.4.1.1.4.1.1.9
-- 1.3.6.1.4.1.1.4.1.1.11
		-- 1.3.6.1.4.1.11001.3.1.1.11
		currentAlarmDeviceID OBJECT-TYPE
			SYNTAX Unsigned32
			MAX-ACCESS read-only
			STATUS current
			DESCRIPTION
				"Description."
			::= { currentAlarmEntry 11 }

		
--   1.3.6.1.4.1.1.4.1.1.10
-- 1.3.6.1.4.1.1.4.1.1.12
		-- 1.3.6.1.4.1.11001.3.1.1.12
		currentAlarmDeviceType OBJECT-TYPE
			SYNTAX INTEGER
				{
				gscBoard(1),
				gtsBoard(2),
				lisuBoard(3)
				}
			MAX-ACCESS read-only
			STATUS current
			DESCRIPTION
				"Description."
			::= { currentAlarmEntry 12 }

		
--   1.3.6.1.4.1.1.4.1.1.11
-- 1.3.6.1.4.1.1.4.1.1.13
		-- 1.3.6.1.4.1.11001.3.1.1.13
		currentAlarmDeviceAddr OBJECT-TYPE
			SYNTAX IpAddress
			MAX-ACCESS read-only
			STATUS current
			DESCRIPTION
				"Description."
			::= { currentAlarmEntry 13 }

		
--   1.3.6.1.4.1.1.4.1.1.12
-- 1.3.6.1.4.1.1.4.1.1.14
		-- 1.3.6.1.4.1.11001.3.1.1.14
		currentAlarmAddtionalText OBJECT-TYPE
			SYNTAX OCTET STRING
			MAX-ACCESS read-only
			STATUS current
			DESCRIPTION
				"Description."
			::= { currentAlarmEntry 14 }

		
--   1.3.6.1.4.1.1.4.1.1.13
-- 1.3.6.1.4.1.1.4.1.1.15
		-- 1.3.6.1.4.1.11001.3.1.1.15
		currentAlarmProposeRepairAction OBJECT-TYPE
			SYNTAX OCTET STRING
			MAX-ACCESS read-only
			STATUS current
			DESCRIPTION
				"Description."
			::= { currentAlarmEntry 15 }

		
		-- 1.3.6.1.4.1.11001.3.1.1.16
		currentAlarmClearAction OBJECT-TYPE
			SYNTAX INTEGER
				{
				manual(0),
				automatic(1)
				}
			MAX-ACCESS read-only
			STATUS current
			DESCRIPTION
				"Description."
			::= { currentAlarmEntry 16 }

		
--   1.3.6.1.4.1.1.4.2
-- 1.3.6.1.4.1.1.4.2
		-- 1.3.6.1.4.1.11001.3.2
		supportedAlarmTable OBJECT-TYPE
			SYNTAX SEQUENCE OF SupportedAlarmEntry
			MAX-ACCESS not-accessible
			STATUS current
			DESCRIPTION
				"store all the supported alarms"
			::= { alarm 2 }

		
--   1.3.6.1.4.1.1.4.2.1
-- 1.3.6.1.4.1.1.4.2.1
		-- 1.3.6.1.4.1.11001.3.2.1
		supportedAlarmEntry OBJECT-TYPE
			SYNTAX SupportedAlarmEntry
			MAX-ACCESS not-accessible
			STATUS current
			DESCRIPTION
				"Description."
			INDEX { supportedAlarmIndex }
			::= { supportedAlarmTable 1 }

		
		SupportedAlarmEntry ::=
			SEQUENCE { 
				supportedAlarmIndex
					Unsigned32,
				supportedAlarmName
					OCTET STRING,
				supportedAlarmNotifyOID
					OBJECT IDENTIFIER,
				supportedAlarmEventType
					INTEGER,
				supportedAlarmProbableCause
					OCTET STRING,
				supportedAlarmPerceivedSeverity
					INTEGER,
				supportedAlarmProposeRepairAction
					OCTET STRING,
				supportedAlarmReportingMechanism
					INTEGER,
				supportedAlarmClearAction
					INTEGER
			 }

--   1.3.6.1.4.1.1.4.2.1.1
-- 1.3.6.1.4.1.1.4.2.1.1
		-- 1.3.6.1.4.1.11001.3.2.1.1
		supportedAlarmIndex OBJECT-TYPE
			SYNTAX Unsigned32 (1..65534)
			MAX-ACCESS not-accessible
			STATUS current
			DESCRIPTION
				"Description."
			::= { supportedAlarmEntry 1 }

		
--   1.3.6.1.4.1.1.4.2.1.2
-- 1.3.6.1.4.1.1.4.2.1.2
		-- 1.3.6.1.4.1.11001.3.2.1.2
		supportedAlarmName OBJECT-TYPE
			SYNTAX OCTET STRING
			MAX-ACCESS read-only
			STATUS current
			DESCRIPTION
				"Description."
			::= { supportedAlarmEntry 2 }

		
--   1.3.6.1.4.1.1.4.2.1.3
-- 1.3.6.1.4.1.1.4.2.1.3
		-- 1.3.6.1.4.1.11001.3.2.1.3
		supportedAlarmNotifyOID OBJECT-TYPE
			SYNTAX OBJECT IDENTIFIER
			MAX-ACCESS read-only
			STATUS current
			DESCRIPTION
				"Description."
			::= { supportedAlarmEntry 3 }

		
--   1.3.6.1.4.1.1.4.2.1.4
-- 1.3.6.1.4.1.1.4.2.1.4
		-- 1.3.6.1.4.1.11001.3.2.1.4
		supportedAlarmEventType OBJECT-TYPE
			SYNTAX INTEGER
				{
				commnicationAlarm(1),
				deviceAlarm(2),
				dataProcessingAlarm(3),
				qualityServiceAlarm(4),
				environmentAlarm(5),
				integrityAlarm(6),
				securityAlarm(7),
				timezoneAlarm(8),
				operationAlarm(9),
				physicalAlarm(10)
				}
			MAX-ACCESS read-write
			STATUS current
			DESCRIPTION
				"Description."
			::= { supportedAlarmEntry 4 }

		
--   1.3.6.1.4.1.1.4.2.1.5
-- 1.3.6.1.4.1.1.4.2.1.5
		-- 1.3.6.1.4.1.11001.3.2.1.5
		supportedAlarmProbableCause OBJECT-TYPE
			SYNTAX OCTET STRING
			MAX-ACCESS read-only
			STATUS current
			DESCRIPTION
				"Description."
			::= { supportedAlarmEntry 5 }

		
--   1.3.6.1.4.1.1.4.2.1.7
-- 1.3.6.1.4.1.1.4.2.1.7
		-- 1.3.6.1.4.1.11001.3.2.1.6
		supportedAlarmPerceivedSeverity OBJECT-TYPE
			SYNTAX INTEGER
				{
				critical(1),
				major(2),
				minor(3),
				warning(4),
				indeterminate(5),
				cleared(6)
				}
			MAX-ACCESS read-write
			STATUS current
			DESCRIPTION
				"Description."
			::= { supportedAlarmEntry 6 }

		
		-- 1.3.6.1.4.1.11001.3.2.1.7
		supportedAlarmProposeRepairAction OBJECT-TYPE
			SYNTAX OCTET STRING
			MAX-ACCESS read-write
			STATUS current
			DESCRIPTION
				"Description."
			::= { supportedAlarmEntry 7 }

		
--   1.3.6.1.4.1.1.4.2.1.8
-- 1.3.6.1.4.1.1.4.2.1.8
		-- 1.3.6.1.4.1.11001.3.2.1.8
		supportedAlarmReportingMechanism OBJECT-TYPE
			SYNTAX INTEGER
				{
				expedited(1),
				pending(2),
				logged(3)
				}
			MAX-ACCESS read-write
			STATUS current
			DESCRIPTION
				"Description."
			::= { supportedAlarmEntry 8 }

		
		-- 1.3.6.1.4.1.11001.3.2.1.9
		supportedAlarmClearAction OBJECT-TYPE
			SYNTAX INTEGER
				{
				manual(0),
				automatic(1)
				}
			MAX-ACCESS read-write
			STATUS current
			DESCRIPTION
				"Description."
			::= { supportedAlarmEntry 9 }

		
--   1.3.6.1.4.1.1.6
-- 1.3.6.1.4.1.1.6
		-- 1.3.6.1.4.1.11001.4
		notification OBJECT IDENTIFIER ::= { grmAgentxMIB 4 }

		
		-- 1.3.6.1.4.1.11001.4.1
		grmStartUp NOTIFICATION-TYPE
			OBJECTS { currentAlarmRaisedTime, currentAlarmAddtionalText }
			STATUS current
			DESCRIPTION 
				"Description."
			::= { notification 1 }

		
--   1.3.6.1.4.1.1.6.1
-- 1.3.6.1.4.1.1.6.1
		-- 1.3.6.1.4.1.11001.4.2
		softwareCrash NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { notification 2 }

		
--   1.3.6.1.4.1.1.6.2
-- 1.3.6.1.4.1.1.6.2
		-- 1.3.6.1.4.1.11001.4.3
		lanLinkFailure NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { notification 3 }

		
--   1.3.6.1.4.1.1.6.9
-- 1.3.6.1.4.1.1.6.9
		-- 1.3.6.1.4.1.11001.4.4
		invalidConfigurationParameter NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { notification 4 }

		
--   1.3.6.1.4.1.1.6.11
-- 1.3.6.1.4.1.1.6.11
		-- 1.3.6.1.4.1.11001.4.5
		excessiveCPUusage NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { notification 5 }

		
--   1.3.6.1.4.1.1.6.12
-- 1.3.6.1.4.1.1.6.12
		-- 1.3.6.1.4.1.11001.4.6
		excessiveMemoryUsage NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { notification 6 }

		
--   1.3.6.1.4.1.1.6.13
-- 1.3.6.1.4.1.1.6.13
		-- 1.3.6.1.4.1.11001.4.7
		gmrProtocolFailure NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { notification 7 }

		
--   1.3.6.1.4.1.1.6.14
-- 1.3.6.1.4.1.1.6.14
		-- 1.3.6.1.4.1.11001.4.8
		beamSetupFailure NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { notification 8 }

		
--   1.3.6.1.4.1.1.6.18
-- 1.3.6.1.4.1.1.6.18
		-- 1.3.6.1.4.1.11001.4.9
		accessSuccTooLow NOTIFICATION-TYPE
			OBJECTS { currentAlarmRaisedTime, currentAlarmChangedTime, currentAlarmSpecificProblem, currentAlarmDeviceID, currentAlarmDeviceType, 
				currentAlarmDeviceAddr, currentAlarmAddtionalText }
			STATUS current
			DESCRIPTION 
				"Description."
			::= { notification 9 }

		
		-- 1.3.6.1.4.1.11001.5
		gssConfigInfoGroup OBJECT-GROUP
			OBJECTS { gssGwId, gssGwType, gssLongtitude, gssLatitude, gssPrimaryMode, 
				gssFrameStartTime, gssConfigMaxEIRP, gssSupportMaxEIRP, gscBeamAccessBeamId, gscBeamAccessMinSigValue, 
				gscBeamAccessTimeoutCounter, gscBeamAccessAreaUpdatePeriod, gscBeamAccessMaxRetry, gscBeamAccessDenyWaitTime, gscBeamAccessPermitBlockNum, 
				gscBeamAccessUeMaxPower, gscBeamAccessDacchAssignTimeout, gscBeamAccessDtchAssignTimeout, gscBeamAccessDtchDelayReleaseTimeout, gscBeamAccessPacketRemain, 
				gscBeamAccessRouteUpdatePeriod, gscBeamAccessPacketWaitUpAssignTimeout, gscBeamAccessPacketDenyWaitTimeout, gscBeamAccessPdtchAssignTimeout, gscBeamAccessPacketRqTimeout, 
				gscBeamAccessReportTime, gscBeamAccessRowstatus, gscCcchVersionID, gscCcchAssignTime, gscCcchBeamId, 
				gscCcchFrameOffset, gscCcchBeamUpPowerLimit, gscCcchBeamDownPowerLimit, gscCcchCarrFreq, gscCcchCarrUpPowerLimit, 
				gscCcchCarrDownPowerLimit, gscCcchCarrDirection, gscCcchCarrSlotNo, gscCcchCarrSlotLen, gscCcchCncarrType, 
				gscCcchLogicChannelType, gscCcchLogicChannelConfig, gscCcchRowStatus, gscTchAssignTime, gscTchVersionID, 
				gscTchBeamId, gscTchFrameOffset, gscTchBeamUpPowerLimit, gscTchBeamDownPowerLimit, gscTchCarrAllocation, 
				gscTchCarrDirection, gscTchCarrUpPowerLimit, gscTchCarrDownPowerLimit, gscTchCSPSFlag, gscTchCarrSlot, 
				gscTchRowStatus, gscBeamSyncAssignTime, gscBeamSyncVersionID, gscBeamSyncCcchFreqNum, gscBeamSyncSacId, 
				gscBeamSyncLacId, gscBeamSyncRacId, gscBeamSyncPlmnMcc, gscBeamSyncPlmnMnc, gscSysInfoRandomizationPeriod, 
				gscSysInfo1ARachControlMaxRetrans, gscSysInfo1ARachControlAccessClasses, gscSysInfo1ARachControlCellBarAccess, gscSysInfo1AMiscInfoClass1SBReselectionHystersis, gscSysInfo1ALsbchPresent, 
				gscSysInfo2AbisSelectionCriterionClass2RXLEVSelectMin, gscSysInfo2AbisMiscInformationClass2SBSelectionPower, gscSysInfo2AbisLAIClass2NPageOccurrences, gscSysInfo3ASBReselectionTimer, gscSysInfo3BbisSBMask, 
				gscSysInfo3BbisImplicitDetachTimer, gscSysInfo3GbisPriorityAccessThreshold, gscSysInfo3GbisLinkFailureMeasurementInterval, gscSysInfo3GbisMACForwardTSOffset, gscSysInfo3GbisMACReturenTSOffset, 
				gscSysInfo3ILAIClass3PauseTimer, gscSysInfo3ILAIClass3RACHAccessTimer, gscSysInfo3ILAIClass3AlertTimer, gscSysInfo3ILAIClass3PagingTimer, gscSysInfo3IPeriodicLUTimer, 
				gscSysInfo3IDualModeHoldTimer, gscSysInfo3IPositionParaRACHPositionTimer, gscSysInfo3IPositionParaGPSUpdateTimer, gscSysInfo3IPositionParaGPSUpdateDistance, gscSysInfo3IPositionParaGPSPositionAge, 
				gscSysInfo3IPositionParaPageGPSPositionAge, gscSysInfo3IPositionParaPageResponseCurrentGPS, gscSysInfo3IPositionParaPositionReportingRequired, gscBeamSyncBeamID, gscSysInfoOthersRowStatus, 
				gscSysInfoOthersBeamID, gscSysInfo4CBeamID, gscSysInfo3IBeamID, gscSysInfo3GbisBeamID, gscSysInfo2AbisBeamID, 
				gscSysInfo1ABeamID, gscSysInfo4ARadioLinkTimeout, gscBeamSyncRowStatus, gscSysInfo1AAssignTime, gscSysInfo1AVersionID, 
				gscSysInfo1ARowStatus, gscSysInfo2AbisAssignTime, gscSysInfo2AbisVersionID, gscSysInfo2AbisLAIClass2RACHTsOffset, gscSysInfo2AbisRowStatus, 
				gscSysInfo3GbisAssignTime, gscSysInfo3GbisVersionID, gscSysInfo3GbisRowStatus, gscSysInfo3IAssignTime, gscSysInfo3IVersionID, 
				gscSysInfo3IRowStatus, gscSysInfo4CAssignTime, gscSysInfo4CVersionID, gscSysInfo4CHHTSQT, gscSysInfo4CHHTDataSQT, 
				gscSysInfo4CVTSQT, gscSysInfo4CVTDataSQT, gscSysInfo4CFTSQT, gscSysInfo4CFTDataSQT, gscSysInfo4CPANinit, 
				gscSysInfo4CPANmin, gscSysInfo4CPANmax, gscSysInfo4CGainUp, gscSysInfo4CGainDn, gscSysInfo4COlthresh, 
				gscSysInfo4COlupGain, gscSysInfo4COldnGain, gscSysInfo4CVarUp, gscSysInfo4CVarDn, gscSysInfo4CSQIfactor, 
				gscSysInfo4CMestep, gscSysInfo4CLQIn1, gscSysInfo4CLQIn2, gscSysInfo4CRowStatus, gscSysInfoOthersAssignTime, 
				gscSysInfoOthersVersionID }
			STATUS current
			DESCRIPTION 
				"Description."
			::= { grmAgentxMIB 5 }

		
		-- 1.3.6.1.4.1.11001.6
		grmTotalInfoGroup OBJECT-GROUP
			OBJECTS { grmSoftwareStatus, grmPortSctp, grmCoGSCIp, grmCoGSCPort, grmCoGSCRowStatus, 
				grmCoOpcIp, grmCoOpcPort }
			STATUS current
			DESCRIPTION 
				"Description."
			::= { grmAgentxMIB 6 }

		
--   1.3.6.1.4.1.1.24
-- 1.3.6.1.4.1.1.24
		-- 1.3.6.1.4.1.11001.7
		currentAlarmGroup OBJECT-GROUP
			OBJECTS { currentAlarmName, currentAlarmNotifyOID, currentAlarmRaisedTime, currentAlarmChangedTime, currentAlarmEventType, 
				currentAlarmProbableCause, currentAlarmSpecificProblem, currentAlarmPerceivedSeverity, currentAlarmReportingMechanism, currentAlarmDeviceID, 
				currentAlarmDeviceType, currentAlarmDeviceAddr, currentAlarmAddtionalText, currentAlarmProposeRepairAction, currentAlarmClearAction
				 }
			STATUS current
			DESCRIPTION 
				"Description."
			::= { grmAgentxMIB 7 }

		
--   1.3.6.1.4.1.1.23
-- 1.3.6.1.4.1.1.23
		-- 1.3.6.1.4.1.11001.8
		supprotedAlarmGroup OBJECT-GROUP
			OBJECTS { supportedAlarmPerceivedSeverity, supportedAlarmProbableCause, supportedAlarmEventType, supportedAlarmProposeRepairAction, supportedAlarmClearAction, 
				supportedAlarmName, supportedAlarmReportingMechanism, supportedAlarmNotifyOID }
			STATUS current
			DESCRIPTION 
				"Description."
			::= { grmAgentxMIB 8 }

		
--   1.3.6.1.4.1.1.30
-- 1.3.6.1.4.1.1.30
		-- 1.3.6.1.4.1.11001.9
		notificationGroup NOTIFICATION-GROUP
			NOTIFICATIONS { softwareCrash, lanLinkFailure, invalidConfigurationParameter, excessiveCPUusage, excessiveMemoryUsage, 
				beamSetupFailure, grmStartUp, accessSuccTooLow, gmrProtocolFailure }
			STATUS current
			DESCRIPTION 
				"Description."
			::= { grmAgentxMIB 9 }

		
	
	END

--
-- GRM-MIB.my
--
